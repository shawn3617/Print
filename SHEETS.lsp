;;; ==========================================================================
;;;  SHEETS.lsp — форматы листов со штампом (ГОСТ Р 21.101, формы 3, 4, 5, 6),
;;;  ведомость листов, ведомость спецификаций, ведомость ссылочных и прилагаемых документов.
;;;  Версия s0.12 (s0.12 — перевод листов СПДС в SHEETS: SHEET_FROM_SPDS;
;;;  s0.11 — окна в виде штампа: «Данные комплекта», «Данные бокового штампа»,
;;;  «Все поля штампа» с кнопками «Для этого листа» / «Для всех листов», шаблоны данных комплекта;
;;;  s0.10 — формы 4 и 5, лист без бокового штампа, ведомость ссылочных и прилагаемых
;;;  документов SHEET_REFS, документы форм 4 и 5 со своей нумерацией; пробная SHEET_TBLTEST убрана;
;;;  s0.9.1 — пробная команда SHEET_TBLTEST: способы убрать рамку заголовка таблицы;
;;;  s0.9 — заголовок ведомостей без рамки: «без границ» на всю строку заголовка;
;;;  s0.8 — окно всех команд SHT, автозагрузка при открытии чертежа;
;;;  s0.7 — подписи и логотип в штампе: SHEET_SIGN, шаг плана s0.4;
;;;  s0.6.2 — ведомость листов вставляется по верху заголовка, как ведомость спецификаций;
;;;  s0.6.1 — ведомость спецификаций обновляется сразу после правки заголовка / переноса таблицы;
;;;  s0.6 — ведомость спецификаций: таблицы AutoCAD «Спецификация…» по листам, SHEET_SPEC;
;;;  s0.5.1 — заголовок ведомости без рамки; удалили лист — ведомость сразу;
;;;  s0.5 — ведомость рабочих чертежей: таблица AutoCAD, «Примечание» по изменениям,
;;;  «Листов» на первом листе, автообновление при сохранении и печати;
;;;  s0.3.2 — печать в PDF: один файл комплекта или отдельные листы, по номерам листов;
;;;  s0.2.2 — тонкий текст, вписывание, короткий штамп, окно листа, формат в «Свойствах»), 2026-10-05
;;;  AutoCAD 2021 / 2024.
;;;  ВАЖНО: файл хранится в кодировке Windows-1251 (ANSI). В UTF-8 кириллица
;;;  в окнах и в чертеже превращается в «кракозябры».
;;;  Команды: SHEET_NEW — новый лист; SHEET_EDIT — изменить лист (и двойной щелчок по листу);
;;;  SHEET_DATA — данные комплекта (во все листы); SHEET_UPDATE — вписать тексты во всех листах;
;;;  SHEET_DBLCLICK — двойной щелчок: окно листа / обычный редактор; SHEET_PROBE — разбор объекта;
;;;  SHEET_APPLY — перестроить листы, у которых в «Свойствах» поменяли FORMAT / ORIENT (запускается сама);
;;;  SHEET_PLOT — печать листов в PDF (s0.3); SHEET_LIST — ведомость рабочих чертежей (s0.5);
;;;  SHEET_SPEC — ведомость спецификаций (s0.6); SHEET_SIGN — подписи и логотип (s0.7);
;;;  SHT — окно всех команд + автозагрузка (s0.8); SHEET_REFS — ведомость ссылочных и прилагаемых
;;;  документов (s0.10); SHEET_STAMP — все поля штампа листа, SHEET_SIDE — данные бокового штампа (s0.11);
;;;  SHEET_FROM_SPDS — перевод листов (рамок) СПДС в листы SHEETS (s0.12).
;;;
;;;  Окна (DCL) встроены в этот файл: при запуске пишутся во временный файл
;;;  и удаляются после закрытия. История и план работ — claude/sheets_state.md
;;; ==========================================================================

(vl-load-com)

;;; --------------------------------------------------------------------------
;;;  1. НАСТРОЙКИ И СПРАВОЧНИКИ (размеры — мм листа; в модели — x масштаб)
;;; --------------------------------------------------------------------------

(setq *sht:Version* "s0.14.4")
(setq *sht:BlkVer* "5")          ; s0.12.1: форма 3 — тексты 2,5, объект на всю графу; версия описаний блоков листа: поменялась — блоки переопределяются
                                 ; s0.2: тексты 0,25, атрибуты на слое листа, форма 6;
                                 ; s0.2.2: формат (графа 26) — атрибут FORMAT, ориентация — ORIENT

;; Кодировка временного DCL-файла (как в PYLON_BASE): nil — ANSI, проверено на 2021/2024
(setq *sht:DclEncoding* nil)

(setq *sht:LayFmt*   "0000_Формат"      ; листы
      *sht:LayFmtP*  "0000_Формат_П"    ; рамка сквозного номера (стадия П) — выключается для Р
      *sht:LayProps* '(("0000_Формат" 7 50) ("0000_Формат_П" 7 50) ("0000_Таблицы" 7 -3))
      *sht:Style*    "ГОСТ 2.304"       ; стиль текста штампа (как в образце СПДС)
      *sht:StyleFont* "CS_Gost2304.shx"
      *sht:SetKey*   "SHT_SET"          ; словарь чертежа: данные комплекта
      *sht:LwThick*  60                 ; основные линии 0,6
      *sht:LwThin*   25                 ; тонкие 0,25 (и обрезная рамка)
      *sht:LwText*   25                 ; толщина текстов и атрибутов (как в образце; не «жирные», s0.2)
      *sht:MinWf*    0.5                ; сжатие длинного текста не сильнее…
      *sht:MinH*     1.8                ; …дальше уменьшается высота, но не ниже 1,8 мм листа
      *sht:LineSp*   1.667)             ; шаг строк многострочного текста, в высотах

;; Поля листа: слева, снизу, справа, сверху (подшивка — слева)
(setq *sht:Margins* '(20.0 5.0 5.0 5.0))

;; Форматы — из «DWG To PDF.pmp» Артёма: (имя кратность короткая длинная), мм.
;; Кратность 1 — основной формат. A4 горизонтальный пока не используется (решение Артёма).
(setq *sht:Formats*
  '(("A4" 1 210.0 297.0) ("A4" 3 297.0 630.0) ("A4" 4 297.0 841.0) ("A4" 5 297.0 1051.0)
    ("A4" 6 297.0 1261.0) ("A4" 7 297.0 1471.0) ("A4" 8 297.0 1682.0) ("A4" 9 297.0 1892.0)
    ("A3" 1 297.0 420.0) ("A3" 3 420.0 891.0) ("A3" 4 420.0 1189.0) ("A3" 5 420.0 1486.0)
    ("A3" 6 420.0 1783.0) ("A3" 7 420.0 2080.0)
    ("A2" 1 420.0 594.0) ("A2" 3 594.0 1261.0) ("A2" 4 594.0 1682.0) ("A2" 5 594.0 2102.0)
    ("A1" 1 594.0 841.0) ("A1" 3 841.0 1783.0) ("A1" 4 841.0 2378.0)
    ("A0" 1 841.0 1189.0) ("A0" 2 1189.0 1682.0) ("A0" 3 1189.0 2523.0)))
(setq *sht:FmtNames* '("A4" "A3" "A2" "A1" "A0"))
(setq *sht:OnlyPortrait* '(("A4" . 1)))   ; только вертикальный

;; Формы штампа (s0.10, образец Артёма «Форматы.dxf»): "3" — основная надпись 185 x 55 (чертежи
;; основного комплекта); "4" — 185 x 55 (чертежи строительных изделий); "5" — 185 x 40 (первый лист
;; текстовых документов, эскизов изделий); "6" — короткая 185 x 15 (последующие листы, «ШтампТекст»).
;; Буква "N" после номера — лист без бокового штампа (поля подшивки): "3N", "4N" …
(setq *sht:Forms*     '("3" "4" "5" "6")
      *sht:FormsAll*  '("3" "4" "5" "6" "3N" "4N" "5N" "6N")
      *sht:FormNames* '("Форма 3 - чертежи основного комплекта (185 x 55)"
                        "Форма 4 - чертежи строительных изделий (185 x 55)"
                        "Форма 5 - текстовые документы, 1-й лист (185 x 40)"
                        "Форма 6 - последующие листы (185 x 15)"))

;; Номер формы без "N"; есть ли боковой штамп; форма из номера и признака
(defun sht:fbase (form) (substr form 1 1))
(defun sht:fside-p (form) (not (wcmatch form "*N")))
(defun sht:fmake (base side) (if side base (strcat base "N")))
;; Лист документа формы 4 / 5 (s0.10): в графе 1 — своё обозначение (атрибут OBOZN, не общий шифр),
;; нумерация — своя внутри документа
(defun sht:fdoc-p (form) (member (sht:fbase form) '("4" "5")))

;; Геометрия — по образцам Артёма (СПДС GraphiCS: «Штампы и таблица.dxf» — форма 3,
;; «ШтампТекст.dxf» — форма 6). Точки — от угла рамки поля: "BR" правый нижний (штамп),
;; "BL" левый нижний (доп. графы), "TR" правый верхний (рамка сквозного номера).
;; Линии: (угол x1 y1 x2 y2 вес слой); слой nil — 0, "P" — *sht:LayFmtP*.
(setq *sht:Lines3*
  '(;; основная надпись (форма 3, 185 x 55)
    ("BR" -185.0 0.0 0.0 0.0 60 nil) ("BR" -185.0 55.0 0.0 55.0 60 nil) ("BR" -185.0 30.0 0.0 30.0 60 nil)
    ("BR" -185.0 35.0 -120.0 35.0 60 nil) ("BR" -120.0 15.0 0.0 15.0 60 nil) ("BR" -120.0 45.0 0.0 45.0 60 nil)
    ("BR" -50.0 25.0 0.0 25.0 60 nil)
    ("BR" -185.0 0.0 -185.0 55.0 60 nil) ("BR" -165.0 0.0 -165.0 55.0 60 nil) ("BR" -145.0 0.0 -145.0 55.0 60 nil)
    ("BR" -130.0 0.0 -130.0 55.0 60 nil) ("BR" -120.0 0.0 -120.0 55.0 60 nil) ("BR" 0.0 0.0 0.0 55.0 60 nil)
    ("BR" -175.0 30.0 -175.0 55.0 60 nil) ("BR" -155.0 30.0 -155.0 55.0 60 nil)
    ("BR" -50.0 0.0 -50.0 30.0 60 nil) ("BR" -35.0 15.0 -35.0 30.0 60 nil) ("BR" -20.0 15.0 -20.0 30.0 60 nil)
    ("BR" -185.0 5.0 -120.0 5.0 25 nil) ("BR" -185.0 10.0 -120.0 10.0 25 nil) ("BR" -185.0 15.0 -120.0 15.0 25 nil)
    ("BR" -185.0 20.0 -120.0 20.0 25 nil) ("BR" -185.0 25.0 -120.0 25.0 25 nil) ("BR" -185.0 40.0 -120.0 40.0 25 nil)
    ("BR" -185.0 45.0 -120.0 45.0 25 nil) ("BR" -185.0 50.0 -120.0 50.0 25 nil)))
(setq *sht:Lines6*
  '(;; короткая (форма 6, 185 x 15): 2 строки изменений + шапка, графа 1 (110), «Лист» 10 x (7 + 8)
    ("BR" -185.0 15.0 0.0 15.0 60 nil) ("BR" -185.0 0.0 -185.0 15.0 60 nil) ("BR" -175.0 0.0 -175.0 15.0 60 nil)
    ("BR" -165.0 0.0 -165.0 15.0 60 nil) ("BR" -155.0 0.0 -155.0 15.0 60 nil) ("BR" -145.0 0.0 -145.0 15.0 60 nil)
    ("BR" -130.0 0.0 -130.0 15.0 60 nil) ("BR" -120.0 0.0 -120.0 15.0 60 nil) ("BR" -10.0 0.0 -10.0 15.0 60 nil)
    ("BR" -10.0 8.0 0.0 8.0 60 nil) ("BR" 0.0 0.0 0.0 15.0 60 nil)
    ("BR" -185.0 5.0 -120.0 5.0 25 nil) ("BR" -185.0 10.0 -120.0 10.0 25 nil)))
(setq *sht:Lines4*
  '(;; форма 4 (185 x 55, «Форматы.dxf»): слева — как у формы 3; справа графа 1 (y 40…55), графа 5
    ;; 70 x 25, «Стадия / Масса / Масштаб» (шапка y 35…40), «Лист / Листов» в одну строку (y 15…20),
    ;; внизу графы 23 (70 x 15) и 9 (50 x 15)
    ("BR" -185.0 0.0 0.0 0.0 60 nil) ("BR" -185.0 55.0 0.0 55.0 60 nil) ("BR" -185.0 30.0 -120.0 30.0 60 nil)
    ("BR" -185.0 35.0 -120.0 35.0 60 nil) ("BR" -120.0 40.0 0.0 40.0 60 nil) ("BR" -120.0 15.0 0.0 15.0 60 nil)
    ("BR" -50.0 35.0 0.0 35.0 60 nil) ("BR" -50.0 20.0 0.0 20.0 60 nil)
    ("BR" -185.0 0.0 -185.0 55.0 60 nil) ("BR" -165.0 0.0 -165.0 55.0 60 nil) ("BR" -145.0 0.0 -145.0 55.0 60 nil)
    ("BR" -130.0 0.0 -130.0 55.0 60 nil) ("BR" -120.0 0.0 -120.0 55.0 60 nil) ("BR" 0.0 0.0 0.0 55.0 60 nil)
    ("BR" -175.0 30.0 -175.0 55.0 60 nil) ("BR" -155.0 30.0 -155.0 55.0 60 nil)
    ("BR" -50.0 0.0 -50.0 40.0 60 nil) ("BR" -35.0 20.0 -35.0 40.0 60 nil) ("BR" -20.0 20.0 -20.0 40.0 60 nil)
    ("BR" -30.0 15.0 -30.0 20.0 60 nil)
    ("BR" -185.0 5.0 -120.0 5.0 25 nil) ("BR" -185.0 10.0 -120.0 10.0 25 nil) ("BR" -185.0 15.0 -120.0 15.0 25 nil)
    ("BR" -185.0 20.0 -120.0 20.0 25 nil) ("BR" -185.0 25.0 -120.0 25.0 25 nil) ("BR" -185.0 40.0 -120.0 40.0 25 nil)
    ("BR" -185.0 45.0 -120.0 45.0 25 nil) ("BR" -185.0 50.0 -120.0 50.0 25 nil)))
(setq *sht:Lines5*
  '(;; форма 5 (185 x 40): 2 строки изменений (y 30…40), шапка (y 25…30), 5 строк подписей;
    ;; справа графа 1 (y 25…40), графа 5 70 x 25, «Стадия / Лист / Листов» (шапка y 20…25, значения
    ;; y 15…20), графа 9 (50 x 15)
    ("BR" -185.0 0.0 0.0 0.0 60 nil) ("BR" -185.0 40.0 0.0 40.0 60 nil) ("BR" -185.0 30.0 -120.0 30.0 60 nil)
    ("BR" -185.0 25.0 0.0 25.0 60 nil) ("BR" -50.0 15.0 0.0 15.0 60 nil) ("BR" -50.0 20.0 0.0 20.0 60 nil)
    ("BR" -185.0 0.0 -185.0 40.0 60 nil) ("BR" -165.0 0.0 -165.0 40.0 60 nil) ("BR" -145.0 0.0 -145.0 40.0 60 nil)
    ("BR" -130.0 0.0 -130.0 40.0 60 nil) ("BR" -120.0 0.0 -120.0 40.0 60 nil) ("BR" 0.0 0.0 0.0 40.0 60 nil)
    ("BR" -175.0 25.0 -175.0 40.0 60 nil) ("BR" -155.0 25.0 -155.0 40.0 60 nil)
    ("BR" -50.0 0.0 -50.0 25.0 60 nil) ("BR" -35.0 15.0 -35.0 25.0 60 nil) ("BR" -20.0 15.0 -20.0 25.0 60 nil)
    ("BR" -185.0 5.0 -120.0 5.0 25 nil) ("BR" -185.0 10.0 -120.0 10.0 25 nil) ("BR" -185.0 15.0 -120.0 15.0 25 nil)
    ("BR" -185.0 20.0 -120.0 20.0 25 nil) ("BR" -185.0 35.0 -120.0 35.0 25 nil)))
(setq *sht:LinesCommon*
  '(;; дополнительные графы на поле подшивки (инв. № подл., подп. и дата, взам. инв. №, согласовано)
    ("BL" 0.0 0.0 0.0 150.0 60 nil) ("BL" -12.0 0.0 0.0 0.0 60 nil) ("BL" -12.0 0.0 -12.0 85.0 60 nil)
    ("BL" -7.0 0.0 -7.0 85.0 60 nil) ("BL" -12.0 25.0 0.0 25.0 60 nil) ("BL" -12.0 60.0 0.0 60.0 60 nil)
    ("BL" -15.0 85.0 0.0 85.0 60 nil) ("BL" -15.0 85.0 -15.0 150.0 60 nil) ("BL" -10.0 85.0 -10.0 150.0 60 nil)
    ("BL" -15.0 150.0 0.0 150.0 60 nil) ("BL" -10.0 105.0 0.0 105.0 60 nil) ("BL" -10.0 125.0 0.0 125.0 60 nil)
    ("BL" -10.0 140.0 0.0 140.0 60 nil) ("BL" -5.0 85.0 -5.0 150.0 25 nil)
    ;; рамка 10 x 7 — сквозной номер листа (стадия П)
    ("TR" -10.0 -7.0 0.0 -7.0 60 "P") ("TR" -10.0 -7.0 -10.0 0.0 60 "P")
    ("TR" -10.0 0.0 0.0 0.0 60 "P") ("TR" 0.0 -7.0 0.0 0.0 60 "P")))

;; Постоянные надписи: (угол x y текст высота сжатие поворот-град выравн-гор выравн-верт)
;; выравнивание: гор. 0 — влево, 1 — по центру; верт. 0 — по базовой линии, 2 — по середине
(setq *sht:Texts3*
  '(("BR" -180.0 32.5 "Изм." 2.5 1.0 0.0 1 2) ("BR" -170.0 32.5 "Кол. уч." 2.5 0.742 0.0 1 2)
    ("BR" -160.0 32.5 "Лист" 2.5 1.0 0.0 1 2) ("BR" -150.0 32.5 "№ док." 2.5 0.889 0.0 1 2)
    ("BR" -137.5 32.5 "Подп." 2.5 1.0 0.0 1 2) ("BR" -125.0 32.5 "Дата" 2.5 1.0 0.0 1 2)
    ("BR" -42.5 27.5 "Стадия" 2.5 1.0 0.0 1 2) ("BR" -27.5 27.5 "Лист" 2.5 1.0 0.0 1 2)
    ("BR" -10.0 27.5 "Листов" 2.5 1.0 0.0 1 2)))
;; форма 6: в образце подписей граф нет — по ГОСТ (шапка внизу, «Лист» в верхней части клетки)
(setq *sht:Texts6*
  '(("BR" -180.0 2.5 "Изм." 2.5 1.0 0.0 1 2) ("BR" -170.0 2.5 "Кол. уч." 2.5 0.742 0.0 1 2)
    ("BR" -160.0 2.5 "Лист" 2.5 1.0 0.0 1 2) ("BR" -150.0 2.5 "№ док." 2.5 0.889 0.0 1 2)
    ("BR" -137.5 2.5 "Подп." 2.5 1.0 0.0 1 2) ("BR" -125.0 2.5 "Дата" 2.5 1.0 0.0 1 2)
    ("BR" -5.0 11.5 "Лист" 2.5 1.0 0.0 1 2)))
;; формы 4 и 5 (s0.10): подписи граф в образце сдвинуты — по ГОСТ, в середине клеток
(setq *sht:Texts4*
  '(("BR" -180.0 32.5 "Изм." 2.5 1.0 0.0 1 2) ("BR" -170.0 32.5 "Кол. уч." 2.5 0.742 0.0 1 2)
    ("BR" -160.0 32.5 "Лист" 2.5 1.0 0.0 1 2) ("BR" -150.0 32.5 "№ док." 2.5 0.889 0.0 1 2)
    ("BR" -137.5 32.5 "Подп." 2.5 1.0 0.0 1 2) ("BR" -125.0 32.5 "Дата" 2.5 1.0 0.0 1 2)
    ("BR" -42.5 37.5 "Стадия" 2.5 1.0 0.0 1 2) ("BR" -27.5 37.5 "Масса" 2.5 1.0 0.0 1 2)
    ("BR" -10.0 37.5 "Масштаб" 2.5 1.0 0.0 1 2)
    ("BR" -48.5 17.5 "Лист" 2.5 1.0 0.0 0 2) ("BR" -28.5 17.5 "Листов" 2.5 1.0 0.0 0 2)))
(setq *sht:Texts5*
  '(("BR" -180.0 27.5 "Изм." 2.5 1.0 0.0 1 2) ("BR" -170.0 27.5 "Кол. уч." 2.5 0.742 0.0 1 2)
    ("BR" -160.0 27.5 "Лист" 2.5 1.0 0.0 1 2) ("BR" -150.0 27.5 "№ док." 2.5 0.889 0.0 1 2)
    ("BR" -137.5 27.5 "Подп." 2.5 1.0 0.0 1 2) ("BR" -125.0 27.5 "Дата" 2.5 1.0 0.0 1 2)
    ("BR" -42.5 22.5 "Стадия" 2.5 1.0 0.0 1 2) ("BR" -27.5 22.5 "Лист" 2.5 1.0 0.0 1 2)
    ("BR" -10.0 22.5 "Листов" 2.5 1.0 0.0 1 2)))
(setq *sht:TextsCommon*
  '(("BR" -32.5 -3.75 "Формат" 2.5 1.0 0.0 1 0)
    ("BL" -9.5 12.5 "Инв. № подл." 3.0 1.0 90.0 1 2) ("BL" -9.5 42.5 "Подп. и дата" 3.0 1.0 90.0 1 2)
    ("BL" -9.5 72.5 "Взам. инв. №" 3.0 0.992 90.0 1 2) ("BL" -11.21 87.0 "Согласовано" 3.0 1.0 90.0 0 0)))
;; имя формата под рамкой («A4x3») — слева по базовой линии; с s0.2.2 — атрибут FORMAT в этой точке
(setq *sht:FmtText* '("BR" -14.5 -3.75 2.5))

;; Атрибуты: (0 тег 1 подсказка 2 по-умолчанию 3 угол 4 x 5 y 6 высота 7 поворот 8 выравн-гор
;;            9 выравн-верт 10 ширина-ячейки 11 многострочный 12 слой 13 высота-ячейки 14 флаги).
;; Порядок — порядок в окне правки атрибутов. Флаги: 0 — обычный, 1 — невидимый.
;; Графы ГОСТ Р 21.101-2026: 1 SHIFR, 2 OBJECT, 3 BUILDING, 4 TITLE, 6 STAGE, 7 SHEET, 8 SHEETS,
;; 9 ORG, 10-13 ROLE/NAME/(подпись)/DATE, 14-19 изменения C1..C4, 20 INV, 22 VZAM.
;; Форма 6: SHEET, SHIFR, C1..C2 и невидимый TITLE (наименование — для ведомости и окна листа).
;; s0.10: форма 4 — OBOZN (графа 1, своё обозначение листа), TITLE (графа 5), MATER (23), STAGE, MASS (24),
;; SCALE (25), SHEET, SHEETS, ORG, подписи 1-6, изменения C1..C4; форма 5 — OBOZN, TITLE (графа 5), STAGE,
;; SHEET, SHEETS, ORG, подписи 1-5, изменения C1..C2. Без бокового штампа ("N") — нет INV, VZAM, SOGL….
(defun sht:attrs-table (form / b res i y n top ns)
  (setq b (sht:fbase form))
  (cond
    ((= b "6")
     (setq res
       (list
         (list "SHEET" "Лист (графа 7)" "" "BR" -5.0 4.0 3.5 0.0 1 2 9.0 nil nil 8.0 0)
         (list "TITLE" "Наименование листа (для ведомости, не видно)" "" "BR" -65.0 20.0 3.5 0.0 1 2 108.0 nil nil 15.0 1)
         (list "SHIFR" "Обозначение, шифр (графа 1)" "" "BR" -65.0 7.5 5.0 0.0 1 2 108.0 nil nil 15.0 0))
           n   2
           top 0.0
           ns  0))
    ((= b "4")
     (setq res
       (list
         (list "SHEET" "Лист (графа 7)" "" "BR" -35.0 17.5 2.5 0.0 1 2 9.0 nil nil 5.0 0)
         (list "TITLE" "Наименование изделия, документа (графа 5)" "" "BR" -85.0 27.5 3.5 0.0 1 2 66.0 T nil 25.0 0)
         (list "OBOZN" "Обозначение документа (графа 1)" "" "BR" -60.0 47.5 5.0 0.0 1 2 116.0 nil nil 15.0 0)
         (list "MATER" "Материал детали (графа 23)" "" "BR" -85.0 7.5 3.5 0.0 1 2 66.0 T nil 15.0 0)
         (list "STAGE" "Стадия (графа 6)" "" "BR" -42.5 27.5 3.5 0.0 1 2 13.0 nil nil 15.0 0)
         (list "MASS" "Масса (графа 24)" "" "BR" -27.5 27.5 3.5 0.0 1 2 13.0 nil nil 15.0 0)
         (list "SCALE" "Масштаб (графа 25)" "" "BR" -10.0 27.5 3.5 0.0 1 2 18.0 nil nil 15.0 0)
         (list "ORG" "Организация (графа 9)" "" "BR" -25.0 7.5 3.5 0.0 1 2 46.0 T nil 15.0 0))
           n   4
           top 30.0
           ns  6))
    ((= b "5")
     (setq res
       (list
         (list "SHEET" "Лист (графа 7)" "" "BR" -27.5 17.5 2.5 0.0 1 2 13.0 nil nil 5.0 0)
         (list "TITLE" "Наименование документа (графа 5)" "" "BR" -85.0 12.5 3.5 0.0 1 2 66.0 T nil 25.0 0)
         (list "OBOZN" "Обозначение документа (графа 1)" "" "BR" -60.0 32.5 5.0 0.0 1 2 116.0 nil nil 15.0 0)
         (list "STAGE" "Стадия (графа 6)" "" "BR" -42.5 17.5 2.5 0.0 1 2 13.0 nil nil 5.0 0)
         (list "ORG" "Организация (графа 9)" "" "BR" -25.0 7.5 3.5 0.0 1 2 46.0 T nil 15.0 0))
           n   2
           top 25.0
           ns  5))
    (t
     (setq res
       (list
         (list "SHEET" "Лист (графа 7)" "" "BR" -27.5 20.0 2.5 0.0 1 2 13.0 nil nil 10.0 0)
         (list "TITLE" "Наименование изображений (графа 4)" "" "BR" -85.0 7.5 2.5 0.0 1 2 66.0 T nil 15.0 0)
         (list "SHIFR" "Обозначение, шифр (графа 1)" "" "BR" -60.0 50.0 5.0 0.0 1 2 116.0 nil nil 10.0 0)
         (list "OBJECT" "Объект (графа 2)" "" "BR" -60.0 37.5 3.5 0.0 1 2 118.0 T nil 15.0 0)
         (list "BUILDING" "Здание (графа 3)" "" "BR" -85.0 22.5 3.5 0.0 1 2 66.0 T nil 15.0 0)
         (list "STAGE" "Стадия (графа 6)" "" "BR" -42.5 20.0 2.5 0.0 1 2 13.0 nil nil 10.0 0)
         (list "ORG" "Организация (графа 9)" "" "BR" -25.0 7.5 3.5 0.0 1 2 46.0 T nil 15.0 0))
           n   4
           top 30.0
           ns  6)))
  ;; подписи (формы 3, 4 — 6 строк, форма 5 — 5): строка i — от верхней (y top-5..top) к нижней (y 0..5)
  (if (> ns 0)
    (progn
      (setq i 1)
      (repeat ns
        (setq y (- top (* 5.0 i)))
        (setq res (append res
          (list (list (strcat "ROLE" (itoa i)) (strcat "Должность, строка " (itoa i)) (sht:role-def i)
                      "BR" -184.55 (+ y 1.17) 2.5 0.0 0 0 19.0 nil nil 5.0 0)
                (list (strcat "NAME" (itoa i)) (strcat "Фамилия, строка " (itoa i)) ""
                      "BR" -164.55 (+ y 1.17) 2.5 0.0 0 0 19.0 nil nil 5.0 0)
                (list (strcat "DATE" (itoa i)) (strcat "Дата, строка " (itoa i)) ""
                      "BR" -125.0 (+ y 2.5) 2.5 0.0 1 2 9.0 nil nil 5.0 0)))
              i (1+ i)))))
  ;; изменения: C1 — нижняя строка над шапкой (формы 3, 4: y 35..40, форма 5: y 30..35, форма 6: y 5..10)
  (setq i 1)
  (repeat n
    (setq y (+ top (* 5.0 i)))
    (setq res (append res
      (mapcar '(lambda (c)
                 (list (strcat "C" (itoa i) (car c)) (strcat (cadr c) ", изменение " (itoa i)) ""
                       "BR" (caddr c) (+ y 2.5) 2.5 0.0 1 2 9.0 nil nil 5.0 0))
              '(("IZM" "Изм." -180.0) ("KOL" "Кол. уч." -170.0) ("LST" "Лист (Зам., Нов., -)" -160.0)
                ("DOC" "№ док." -150.0) ("DAT" "Дата" -125.0))))
          i (1+ i)))
  ;; боковой штамп (поле подшивки) — если он есть (s0.10)
  (if (sht:fside-p form)
    (setq res (append res
      (list
        (list "INV" "Инв. № подл. (графа 20)" "" "BL" -3.5 12.5 2.5 90.0 1 2 24.0 nil nil 7.0 0)
        (list "VZAM" "Взам. инв. № (графа 22)" "" "BL" -3.5 72.5 2.5 90.0 1 2 24.0 nil nil 7.0 0)
        (list "SOGL1R" "Согласовано 1: должность" "" "BL" -7.5 95.0 2.5 90.0 1 2 19.0 nil nil 5.0 0)
        (list "SOGL1N" "Согласовано 1: фамилия" "" "BL" -7.5 115.0 2.5 90.0 1 2 19.0 nil nil 5.0 0)
        (list "SOGL1D" "Согласовано 1: дата" "" "BL" -7.5 145.0 2.5 90.0 1 2 9.0 nil nil 5.0 0)
        (list "SOGL2R" "Согласовано 2: должность" "" "BL" -2.5 95.0 2.5 90.0 1 2 19.0 nil nil 5.0 0)
        (list "SOGL2N" "Согласовано 2: фамилия" "" "BL" -2.5 115.0 2.5 90.0 1 2 19.0 nil nil 5.0 0)
        (list "SOGL2D" "Согласовано 2: дата" "" "BL" -2.5 145.0 2.5 90.0 1 2 9.0 nil nil 5.0 0)))))
  (setq res (append res
    (list
      (list "PNUM" "Сквозной номер листа (стадия П)" "" "TR" -5.0 -3.5 3.5 0.0 1 2 9.0 nil "P" 7.0 0)
      ;; s0.2.2: формат и ориентация — правятся в «Свойствах», лист перестраивается (SHEET_APPLY)
      (list "FORMAT" "Формат: A3, A4x3 ... (графа 26; изменить - лист перестроится)" ""
            "BR" -14.5 -3.75 2.5 0.0 0 0 19.0 nil nil 5.0 0)
      (list "ORIENT" "Ориентация: горизонтальная / вертикальная (изменить - лист перестроится)" ""
            "BR" -14.5 -3.75 2.5 0.0 0 0 19.0 nil nil 5.0 1))))
  (cond
    ((= b "4")
     (setq res (append res
       (list (list "SHEETS" "Листов (графа 8, только на 1-м листе)" "" "BR" -9.5 17.5 2.5 0.0 1 2 17.0 nil nil 5.0 0)))))
    ((= b "5")
     (setq res (append res
       (list (list "SHEETS" "Листов (графа 8, только на 1-м листе)" "" "BR" -10.0 17.5 2.5 0.0 1 2 18.0 nil nil 5.0 0)))))
    ((/= b "6")
     (setq res (append res
       (list (list "SHEETS" "Листов (графа 8, только на 1-м листе)" "" "BR" -10.0 20.0 2.5 0.0 1 2 18.0 nil nil 10.0 0))))))
  res)

;; Должности по умолчанию (решение Артёма: «Разработал», «Проверил», «Н.контр.» — заранее, все правятся)
(defun sht:role-def (i)
  (cond ((= i 1) "Разработал") ((= i 2) "Проверил") ((= i 4) "Н.контр.") (t "")))

(setq *sht:Attrs*  (sht:attrs-table "3")
      *sht:Attrs6* (sht:attrs-table "6"))
;; s0.10: таблицы атрибутов всех форм (с боковым штампом и без)
(setq *sht:AttrTabs* (mapcar '(lambda (f) (cons f (sht:attrs-table f))) *sht:FormsAll*))

;; Общие для комплекта поля (окно «Данные комплекта»)
(setq *sht:Common*
  '("SHIFR" "OBJECT" "BUILDING" "STAGE" "ORG"
    "ROLE1" "NAME1" "DATE1" "ROLE2" "NAME2" "DATE2" "ROLE3" "NAME3" "DATE3"
    "ROLE4" "NAME4" "DATE4" "ROLE5" "NAME5" "DATE5" "ROLE6" "NAME6" "DATE6"
    "INV" "VZAM" "SOGL1R" "SOGL1N" "SOGL1D" "SOGL2R" "SOGL2N" "SOGL2D"))
(setq *sht:CommonDef* '(("ROLE1" . "Разработал") ("ROLE2" . "Проверил") ("ROLE4" . "Н.контр.")
                        ("STAGE" . "Р")))
;; s0.11: окна в виде штампа. Поля окна «Штамп» (форма 3: изменения сверху вниз — C4 … C1,
;; подписи, правая часть, графы формы 4) и окна «Боковой штамп»; поля только листа (в «Для всех листов»
;; идут лишь в свой лист); поля шаблона данных комплекта (без дат).
(setq *sht:StampTags*
  '("C4IZM" "C4KOL" "C4LST" "C4DOC" "C4DAT" "C3IZM" "C3KOL" "C3LST"
    "C3DOC" "C3DAT" "C2IZM" "C2KOL" "C2LST" "C2DOC" "C2DAT" "C1IZM"
    "C1KOL" "C1LST" "C1DOC" "C1DAT" "ROLE1" "NAME1" "DATE1" "ROLE2"
    "NAME2" "DATE2" "ROLE3" "NAME3" "DATE3" "ROLE4" "NAME4" "DATE4"
    "ROLE5" "NAME5" "DATE5" "ROLE6" "NAME6" "DATE6" "SHIFR" "OBJECT"
    "BUILDING" "STAGE" "SHEET" "SHEETS" "TITLE" "ORG" "MASS" "SCALE"
    "MATER"))
(setq *sht:SideTags* '("INV" "VZAM" "SOGL1R" "SOGL1N" "SOGL1D" "SOGL2R" "SOGL2N" "SOGL2D"))
(setq *sht:OneTags* '("SHEET" "SHEETS" "TITLE" "OBOZN" "MASS" "SCALE" "MATER"))
(setq *sht:TplTags*
  '("SHIFR" "OBJECT" "STAGE" "ORG" "ROLE1" "NAME1" "ROLE2" "NAME2"
    "ROLE3" "NAME3" "ROLE4" "NAME4" "ROLE5" "NAME5" "ROLE6" "NAME6"
    "SOGL1R" "SOGL1N" "SOGL2R" "SOGL2N"))
;; Поле окна для каждого поля штампа (ключи — литералом; графа 1 — "sht_SHIFR", у форм 4, 5 — обозначение)
(setq *sht:FwTiles*
  '(("C4IZM" . "sht_FC4IZM") ("C4KOL" . "sht_FC4KOL") ("C4LST" . "sht_FC4LST") ("C4DOC" . "sht_FC4DOC")
    ("C4DAT" . "sht_FC4DAT") ("C3IZM" . "sht_FC3IZM") ("C3KOL" . "sht_FC3KOL") ("C3LST" . "sht_FC3LST")
    ("C3DOC" . "sht_FC3DOC") ("C3DAT" . "sht_FC3DAT") ("C2IZM" . "sht_FC2IZM") ("C2KOL" . "sht_FC2KOL")
    ("C2LST" . "sht_FC2LST") ("C2DOC" . "sht_FC2DOC") ("C2DAT" . "sht_FC2DAT") ("C1IZM" . "sht_FC1IZM")
    ("C1KOL" . "sht_FC1KOL") ("C1LST" . "sht_FC1LST") ("C1DOC" . "sht_FC1DOC") ("C1DAT" . "sht_FC1DAT")
    ("ROLE1" . "sht_ROLE1") ("NAME1" . "sht_NAME1") ("DATE1" . "sht_DATE1") ("ROLE2" . "sht_ROLE2")
    ("NAME2" . "sht_NAME2") ("DATE2" . "sht_DATE2") ("ROLE3" . "sht_ROLE3") ("NAME3" . "sht_NAME3")
    ("DATE3" . "sht_DATE3") ("ROLE4" . "sht_ROLE4") ("NAME4" . "sht_NAME4") ("DATE4" . "sht_DATE4")
    ("ROLE5" . "sht_ROLE5") ("NAME5" . "sht_NAME5") ("DATE5" . "sht_DATE5") ("ROLE6" . "sht_ROLE6")
    ("NAME6" . "sht_NAME6") ("DATE6" . "sht_DATE6") ("SHIFR" . "sht_SHIFR") ("OBJECT" . "sht_OBJECT")
    ("BUILDING" . "sht_BUILDING") ("STAGE" . "sht_STAGE") ("SHEET" . "sht_FSHEET") ("SHEETS" . "sht_FSHEETS")
    ("TITLE" . "sht_FTITLE") ("ORG" . "sht_ORG") ("MASS" . "sht_FMASS") ("SCALE" . "sht_FSCALE")
    ("MATER" . "sht_FMATER") ("INV" . "sht_INV") ("VZAM" . "sht_VZAM") ("SOGL1R" . "sht_SOGL1R")
    ("SOGL1N" . "sht_SOGL1N") ("SOGL1D" . "sht_SOGL1D") ("SOGL2R" . "sht_SOGL2R") ("SOGL2N" . "sht_SOGL2N")
    ("SOGL2D" . "sht_SOGL2D")))

;; Названия полей — для сообщений
(setq *sht:CommonNames*
  '(("SHIFR" . "шифр") ("OBJECT" . "объект") ("BUILDING" . "здание") ("STAGE" . "стадия")
    ("ORG" . "организация") ("INV" . "инв. № подл.") ("VZAM" . "взам. инв. №")))

;; Алфавиты — порядок букв в номерах листов (1.а, 1.б … / 1.a, 1.b …)
(setq *sht:AbcRu* "абвгдеёжзийклмнопрстуфхцчшщъыьэюя"
      *sht:AbcEn* "abcdefghijklmnopqrstuvwxyz")

;;; --------------------------------------------------------------------------
;;;  2. УМОЛЧАНИЯ (последний выбор — в реестре, setenv)
;;; --------------------------------------------------------------------------

(defun sht:defaults ( / s)
  (if (not *sht_Fmt*)
    (setq *sht_Fmt* (if (member (setq s (getenv "SHT_Fmt")) *sht:FmtNames*) s "A3")))
  (if (not *sht_Mult*)
    (setq *sht_Mult* (if (and (setq s (getenv "SHT_Mult")) (> (atoi s) 0)) (atoi s) 1)))
  (if (not (sht:fmt-rec *sht_Fmt* *sht_Mult*)) (setq *sht_Mult* 1))
  (if (not *sht_Orient*)
    (setq *sht_Orient* (if (member (setq s (getenv "SHT_Orient")) '("L" "P")) s "L")))
  (if (not *sht_Scale*)
    (setq *sht_Scale* (if (and (setq s (getenv "SHT_Scale")) (distof s 2) (> (distof s 2) 0))
                        (distof s 2) 100.0)))
  (if (sht:portrait-only-p *sht_Fmt* *sht_Mult*) (setq *sht_Orient* "P"))
  (if (not *sht_Form*)
    (setq *sht_Form* (if (member (setq s (getenv "SHT_Form")) *sht:FormsAll*) s "3")))
  (if (not *sht_Title*) (setq *sht_Title* "")))

(defun sht:save-defaults ()
  (setenv "SHT_Fmt" *sht_Fmt*)
  (setenv "SHT_Mult" (itoa *sht_Mult*))
  (setenv "SHT_Orient" *sht_Orient*)
  (setenv "SHT_Scale" (sht:n2s *sht_Scale*))
  (setenv "SHT_Form" *sht_Form*))

;;; --------------------------------------------------------------------------
;;;  3. УТИЛИТЫ
;;; --------------------------------------------------------------------------

(defun sht:doc () (vla-get-ActiveDocument (vlax-get-acad-object)))
(defun sht:ms () (vla-get-ModelSpace (sht:doc)))

;; Число -> строка без лишних нулей: 100.0 -> "100", 2.5 -> "2.5"
(defun sht:n2s (x / s)
  (setq s (rtos x 2 3))
  (if (vl-string-search "." s)
    (setq s (vl-string-right-trim "." (vl-string-right-trim "0" s))))
  s)

(defun sht:trim (s) (if s (vl-string-trim " \t" s) ""))

;; Заменить (или добавить в конец) группу code в списке DXF
(defun sht:dxf-set (ed code val)
  (if (assoc code ed)
    (subst (cons code val) (assoc code ed) ed)
    (append ed (list (cons code val)))))

(defun sht:pt+ (p x y) (list (+ (car p) x) (+ (cadr p) y) 0.0))

;; Ширина строки s при высоте h (textbox стиля штампа; запасной — 0,7·h на знак)
(defun sht:str-w (s h / tb)
  (setq tb (vl-catch-all-apply 'textbox (list (list (cons 1 s) (cons 40 h) (cons 7 *sht:Style*)))))
  (if (and tb (not (vl-catch-all-error-p tb)))
    (- (car (cadr tb)) (car (car tb)))
    (* 0.7 h (strlen s))))

;; Строки многострочного текста ("\P" — перенос)
(defun sht:split (s sep / i res)
  (while (setq i (vl-string-search sep s))
    (setq res (cons (substr s 1 i) res)
          s   (substr s (+ i 1 (strlen sep)))))
  (reverse (cons s res)))

;;; --------------------------------------------------------------------------
;;;  4. ФОРМАТЫ И БЛОКИ ЛИСТА
;;; --------------------------------------------------------------------------

(defun sht:fmt-rec (name mult / res)
  (foreach r *sht:Formats*
    (if (and (= (car r) name) (= (cadr r) mult)) (setq res r)))
  res)

(defun sht:mults (name / res)
  (foreach r *sht:Formats*
    (if (= (car r) name) (setq res (cons (cadr r) res))))
  (reverse res))

(defun sht:portrait-only-p (name mult)
  (member (cons name mult) *sht:OnlyPortrait*))

;; «A4», «A4x3» — обозначение формата (графа 26)
(defun sht:fmt-label (rec)
  (if (= (cadr rec) 1) (car rec) (strcat (car rec) "x" (itoa (cadr rec)))))

;; Ширина и высота листа: L — длинная сторона по горизонтали, P — по вертикали
(defun sht:fmt-wh (rec orient)
  (if (= orient "P") (list (caddr rec) (cadddr rec)) (list (cadddr rec) (caddr rec))))

;; Имя блока: SHT_<формат><L|P>[_<форма>] — форма 3 без суффикса; "_4", "_5", "_6" — формы 4, 5, 6
;; (s0.2: "_6"); без бокового штампа (s0.10) — "N": "_N" (форма 3), "_4N", "_5N", "_6N"
(defun sht:bname (rec orient form)
  (strcat "SHT_" (sht:fmt-label rec) orient
          (cond ((= form "3") "") ((= form "3N") "_N") (t (strcat "_" form)))))

;; Имя блока -> (запись-формата ориентация форма) или nil:
;; "SHT_A4x3L" -> (("A4" 3 297 630) "L" "3"); "SHT_A3P_6" -> (("A3" 1 297 420) "P" "6");
;; "SHT_A3L_N" -> (… "L" "3N"); "SHT_A2L_4N" -> (… "L" "4N")
(defun sht:parse-bname (bn / s o lab i rec form k sfx)
  (setq bn   (strcase bn)
        form "3")
  (if (and (> (strlen bn) 4) (setq k (vl-string-search "_" bn 4)))
    (setq sfx  (substr bn (+ k 2))
          bn   (substr bn 1 k)
          form (cond ((= sfx "N") "3N")
                     ((and (member sfx *sht:FormsAll*) (/= sfx "3") (/= sfx "3N")) sfx))))
  (if (and form (wcmatch bn "SHT_A#*") (> (strlen bn) 6))
    (progn
      (setq s   (substr bn 5)
            o   (substr s (strlen s))
            lab (substr s 1 (1- (strlen s))))
      (if (member o '("L" "P"))
        (progn
          (if (setq i (vl-string-search "X" lab))
            (setq rec (sht:fmt-rec (substr lab 1 i) (atoi (substr lab (+ i 2)))))
            (setq rec (sht:fmt-rec lab 1)))
          (if rec (list rec o form)))))))

;; Таблицы формы штампа (s0.10: формы 4, 5; без бокового штампа — без линий, надписей и атрибутов
;; поля подшивки: у них угол "BL")
(defun sht:attr-tab (form) (cond ((cdr (assoc form *sht:AttrTabs*))) (*sht:Attrs*)))
(defun sht:side-filter (form lst)
  (if (sht:fside-p form) lst (vl-remove-if '(lambda (x) (= (car x) "BL")) lst)))
(defun sht:lines-of (form / b)
  (setq b (sht:fbase form))
  (append (cond ((= b "6") *sht:Lines6*) ((= b "4") *sht:Lines4*) ((= b "5") *sht:Lines5*) (t *sht:Lines3*))
          (sht:side-filter form *sht:LinesCommon*)))
(defun sht:texts-of (form / b)
  (setq b (sht:fbase form))
  (append (cond ((= b "6") *sht:Texts6*) ((= b "4") *sht:Texts4*) ((= b "5") *sht:Texts5*) (t *sht:Texts3*))
          (sht:side-filter form *sht:TextsCommon*)))

;; Угол рамки поля в мм листа: "BR", "BL", "TR"
(defun sht:anchor (key wh / m)
  (setq m *sht:Margins*)
  (cond ((= key "BR") (list (- (car wh) (caddr m)) (cadr m)))
        ((= key "BL") (list (car m) (cadr m)))
        ((= key "TR") (list (- (car wh) (caddr m)) (- (cadr wh) (cadddr m))))
        (t (list 0.0 0.0))))

(defun sht:lay-of (code) (if (= code "P") *sht:LayFmtP* "0"))
;; Слой атрибута в описании блока (s0.2): слой листа, рамка сквозного номера — свой слой
(defun sht:att-lay (code) (if (= code "P") *sht:LayFmtP* *sht:LayFmt*))

;; --- примитивы описания блока (entmake внутри BLOCK ... ENDBLK) ---
(defun sht:bd-line (p1 p2 lw lay)
  (entmake (list '(0 . "LINE") (cons 8 lay) (cons 370 lw) (cons 10 p1) (cons 11 p2))))

(defun sht:bd-rect (x1 y1 x2 y2 lw)
  (entmake (list '(0 . "LWPOLYLINE") '(100 . "AcDbEntity") '(8 . "0") (cons 370 lw)
                 '(100 . "AcDbPolyline") '(90 . 4) '(70 . 1)
                 (list 10 x1 y1) (list 10 x2 y1) (list 10 x2 y2) (list 10 x1 y2))))

;; Тексты и атрибуты — толщина 0,25 явно (s0.2: со слоя 0000_Формат брали 0,5 — «жирные»)
(defun sht:bd-text (p s h wf rot hj vj)
  (entmake (list '(0 . "TEXT") '(8 . "0") (cons 370 *sht:LwText*) (cons 10 p) (cons 40 h) (cons 1 s)
                 (cons 50 rot) (cons 41 wf) (cons 7 *sht:Style*)
                 (cons 72 hj) (cons 73 vj) (cons 11 p))))

(defun sht:bd-attdef (p tag prompt def h rot hj vj lay flags)
  (entmake (list '(0 . "ATTDEF") '(100 . "AcDbEntity") (cons 8 lay) (cons 370 *sht:LwText*)
                 '(100 . "AcDbText") (cons 10 p) (cons 40 h) (cons 1 def) (cons 50 rot)
                 '(41 . 1.0) (cons 7 *sht:Style*) (cons 72 hj) (cons 11 p)
                 '(100 . "AcDbAttributeDefinition") (cons 3 prompt) (cons 2 tag) (cons 70 flags)
                 (cons 74 vj))))

(defun sht:deg (a) (* pi (/ a 180.0)))

;; Описание блока листа rec / orient / form (создать или переопределить)
(defun sht:block-def (rec orient form / name wh w h m a l t1 at tab)
  (setq name (sht:bname rec orient form)
        wh   (sht:fmt-wh rec orient)
        w    (car wh)
        h    (cadr wh)
        m    *sht:Margins*
        tab  (sht:attr-tab form))
  (entmake (list '(0 . "BLOCK") (cons 2 name) '(70 . 2) '(10 0.0 0.0 0.0)))
  ;; обрезная рамка (тонкая) и рамка поля
  (sht:bd-rect 0.0 0.0 w h *sht:LwThin*)
  (sht:bd-rect (car m) (cadr m) (- w (caddr m)) (- h (cadddr m)) *sht:LwThick*)
  (foreach l (sht:lines-of form)
    (setq a (sht:anchor (car l) wh))
    (sht:bd-line (sht:pt+ a (nth 1 l) (nth 2 l)) (sht:pt+ a (nth 3 l) (nth 4 l))
                 (nth 5 l) (sht:lay-of (nth 6 l))))
  (foreach t1 (sht:texts-of form)
    (sht:bd-text (sht:pt+ (sht:anchor (car t1) wh) (nth 1 t1) (nth 2 t1))
                 (nth 3 t1) (nth 4 t1) (nth 5 t1) (sht:deg (nth 6 t1)) (nth 7 t1) (nth 8 t1)))
  (foreach at tab
    (sht:bd-attdef (sht:pt+ (sht:anchor (nth 3 at) wh) (nth 4 at) (nth 5 at))
                   (nth 0 at) (nth 1 at) (sht:att-default at rec orient) (nth 6 at) (sht:deg (nth 7 at))
                   (nth 8 at) (nth 9 at) (sht:att-lay (nth 12 at)) (nth 14 at)))
  (entmake '((0 . "ENDBLK")))
  (sht:ml-attdefs name wh tab)
  name)

;; Значение атрибута по умолчанию; FORMAT и ORIENT — формат и ориентация этого блока
;; (ATTSYNC добавит их в листы прежних версий уже с верными значениями)
(defun sht:att-default (at rec orient)
  (cond ((= (car at) "FORMAT") (sht:fmt-label rec))
        ((= (car at) "ORIENT") (sht:orient-name orient))
        (t (nth 2 at))))

(defun sht:orient-name (o) (if (= o "P") "вертикальная" "горизонтальная"))

;; Многострочные атрибуты (графы 2, 3, 4, 9): через ActiveX — свойство MTextAttribute.
;; Не вышло — атрибут остаётся однострочным (длинный текст сжимается по ширине).
(defun sht:ml-attdefs (name wh tab / blk at r n need)
  (setq n    0
        need (vl-some '(lambda (x) (nth 11 x)) tab)
        blk  (vl-catch-all-apply 'vla-Item (list (vla-get-Blocks (sht:doc)) name)))
  (if (and need (not (vl-catch-all-error-p blk)))
    (vlax-for o blk
      (if (and (= (vla-get-ObjectName o) "AcDbAttributeDefinition")
               (setq at (assoc (vla-get-TagString o) tab))
               (nth 11 at))
        (progn
          (setq r (vl-catch-all-apply 'vla-put-MTextAttribute (list o :vlax-true)))
          (if (not (vl-catch-all-error-p r))
            (progn
              (setq n (1+ n))
              (vl-catch-all-apply 'vla-put-MTextBoundaryWidth (list o (nth 10 at)))
              (vl-catch-all-apply 'vla-put-Alignment (list o 10))   ; acAlignmentMiddleCenter
              (vl-catch-all-apply 'vla-put-TextAlignmentPoint
                (list o (vlax-3d-point (sht:pt+ (sht:anchor (nth 3 at) wh) (nth 4 at) (nth 5 at)))))))))))
  (if (and need (= n 0))
    (princ "\n! SHEETS: многострочные атрибуты не созданы - длинный текст будет сжат в одну строку."))
  n)

;; Блок листа есть? Нет — описать.
(defun sht:block-ensure (rec orient form / name)
  (setq name (sht:bname rec orient form))
  (if (not (tblsearch "BLOCK" name))
    (sht:block-def rec orient form))
  name)

;; Версия описаний блоков поменялась — переопределить все блоки листов чертежа (ATTSYNC — атрибуты),
;; затем вписать тексты всех листов заново (ATTSYNC возвращает высоты и сжатие к описанию)
(defun sht:blocks-refresh (sdat / r p n names ce)
  (setq n 0)
  (if (/= (cdr (assoc "@BLKVER" sdat)) *sht:BlkVer*)
    (progn
      ;; сначала собрать имена, потом переопределять (не трогать таблицу блоков во время перебора)
      (setq r (tblnext "BLOCK" T))
      (while r
        (if (sht:parse-bname (cdr (assoc 2 r)))
          (setq names (cons (cdr (assoc 2 r)) names)))
        (setq r (tblnext "BLOCK")))
      (setq ce (getvar "CMDECHO"))
      (setvar "CMDECHO" 0)
      (foreach bn (reverse names)
        (setq p (sht:parse-bname bn))
        (sht:block-def (car p) (cadr p) (caddr p))
        (command "_.ATTSYNC" "_N" bn)
        (setq n (1+ n)))
      (setvar "CMDECHO" ce)
      (if (> n 0)
        (progn
          (sht:fit-all)
          (sht:watch)
          (princ (strcat "\nSHEETS: описания блоков листов обновлены: " (itoa n)))))
      (sht:set-write (sht:alist-put sdat "@BLKVER" *sht:BlkVer*))))
  n)

;;; --------------------------------------------------------------------------
;;;  5. СЛОИ, СТИЛЬ, ДАННЫЕ КОМПЛЕКТА (словарь чертежа SHT_SET)
;;; --------------------------------------------------------------------------

(defun sht:layer (name / pr en ed)
  (setq pr (cdr (assoc name *sht:LayProps*)))
  (if (not pr) (setq pr (list 7 -3)))
  (if (setq en (tblobjname "LAYER" name))
    ;; слой есть: включить, разблокировать (4); заморозку (1) решает sht:stage-layer
    (progn
      (setq ed (entget en)
            ed (sht:dxf-set ed 70 (logand (cond ((cdr (assoc 70 ed))) (0)) (~ 4))))
      (if (< (cond ((cdr (assoc 62 ed))) (7)) 0)
        (setq ed (sht:dxf-set ed 62 (abs (cdr (assoc 62 ed))))))
      (entmod ed))
    (entmake (list '(0 . "LAYER") '(100 . "AcDbSymbolTableRecord") '(100 . "AcDbLayerTableRecord")
                   (cons 2 name) '(70 . 0) (cons 62 (car pr)) '(6 . "Continuous") (cons 370 (cadr pr))))))

;; Стадия П — рамка сквозного номера видна, иначе слой заморожен
(defun sht:stage-layer (stage / en ed fl old frz)
  (setq frz (/= (strcase (sht:trim stage)) "П"))
  (if (setq en (tblobjname "LAYER" *sht:LayFmtP*))
    (progn
      (setq ed  (entget en)
            old (cond ((cdr (assoc 70 ed))) (0))
            fl  old)
      (if (and frz (/= (strcase (getvar "CLAYER")) (strcase *sht:LayFmtP*)))
        (setq fl (logior fl 1))
        (setq fl (logand fl (~ 1))))
      ;; заморозка поменялась — записать и перерисовать
      (if (/= fl old)
        (progn
          (entmod (sht:dxf-set ed 70 fl))
          (vl-catch-all-apply 'vla-Regen (list (sht:doc) 0))))))   ; 0 — acActiveViewport
  (not frz))

(defun sht:style ()
  (if (not (tblsearch "STYLE" *sht:Style*))
    (entmake (list '(0 . "STYLE") '(100 . "AcDbSymbolTableRecord") '(100 . "AcDbTextStyleTableRecord")
                   (cons 2 *sht:Style*) '(70 . 0) '(40 . 0.0) '(41 . 1.0) '(50 . 0.0) '(71 . 0)
                   '(42 . 2.5) (cons 3 *sht:StyleFont*) '(4 . "")))))

;; alist: заменить / добавить пару
(defun sht:alist-put (al key val)
  (if (assoc key al)
    (subst (cons key val) (assoc key al) al)
    (append al (list (cons key val)))))

;; Данные комплекта из словаря чертежа: (("SHIFR" . "…") …), ключи "@…" — служебные
(defun sht:set-read ( / d res key)
  (if (setq d (dictsearch (namedobjdict) *sht:SetKey*))
    (foreach g d
      (cond ((= (car g) 300)
             (setq key (cdr g)
                   res (cons (cons key "") res)))
            ((and key (= (car g) 301))
             (setq res (cons (cons key (strcat (cdar res) (cdr g))) (cdr res)))))))
  (reverse res))

;; Строка -> куски по 250 знаков (группы 301)
(defun sht:chunks (s / res)
  (while (> (strlen s) 250)
    (setq res (cons (cons 301 (substr s 1 250)) res)
          s   (substr s 251)))
  (reverse (cons (cons 301 s) res)))

(defun sht:set-write (al / nod lst old xr)
  (setq nod (namedobjdict)
        lst (list '(0 . "XRECORD") '(100 . "AcDbXrecord")))
  (foreach p al
    (setq lst (append lst (list (cons 300 (car p))) (sht:chunks (cdr p)))))
  (if (setq old (dictsearch nod *sht:SetKey*))
    (progn
      (dictremove nod *sht:SetKey*)
      (vl-catch-all-apply 'entdel (list (cdr (assoc -1 old))))))
  (if (setq xr (entmakex lst))
    (dictadd nod *sht:SetKey* xr)))

;; Подготовка чертежа: стиль, слои, версия блоков. Возвращает данные комплекта.
(defun sht:prepare ()
  (sht:style)
  (sht:layer *sht:LayFmt*)
  (sht:layer *sht:LayFmtP*)
  (sht:blocks-refresh (sht:set-read))
  (sht:set-read))

;;; --------------------------------------------------------------------------
;;;  6. ЛИСТЫ ЧЕРТЕЖА: поиск, атрибуты, номера
;;; --------------------------------------------------------------------------

;; Все листы (вставки SHT_*) в пространстве модели
(defun sht:sheets ( / ss i en ed res)
  (if (setq ss (ssget "_X" '((0 . "INSERT") (2 . "SHT_*"))))
    (progn
      (setq i 0)
      (while (< i (sslength ss))
        (setq en (ssname ss i)
              ed (entget en)
              i  (1+ i))
        (if (and (sht:parse-bname (cdr (assoc 2 ed)))
                 (= (strcase (cond ((cdr (assoc 410 ed))) ("Model"))) "MODEL"))
          (setq res (cons en res))))))
  (reverse res))

(defun sht:att-objs (en / r)
  (setq r (vl-catch-all-apply 'vlax-invoke (list (vlax-ename->vla-object en) 'GetAttributes)))
  (if (vl-catch-all-error-p r) nil r))

;; Атрибуты листа: (("SHEET" . "3") ("TITLE" . "…") …)
(defun sht:attrs (en / res)
  (foreach a (sht:att-objs en)
    (setq res (cons (cons (strcase (vla-get-TagString a)) (vla-get-TextString a)) res)))
  (reverse res))



(defun sht:int-p (s) (and (> (atoi s) 0) (= (itoa (atoi s)) s)))

;; Группа нумерации листа (s0.10): листы форм 4 и 5 нумеруются внутри своего документа (графа 1,
;; OBOZN; без учёта регистра и пробелов по краям), остальные — нумерацией основного комплекта
(defun sht:num-group (form obozn)
  (if (sht:fdoc-p form) (strcat "D:" (sht:lc (sht:trim obozn))) "M"))

;; Номера листов ens по группам: ((группа . номер) …), пустые — нет
(defun sht:gnums (ens / inf a s res)
  (foreach en ens
    (setq inf (sht:sheet-info en)
          a   (sht:attrs en)
          s   (sht:trim (cdr (assoc "SHEET" a))))
    (if (/= s "")
      (setq res (cons (cons (sht:num-group (caddr inf) (cdr (assoc "OBOZN" a))) s) res))))
  (reverse res))

;; Номера группы g из списка sht:gnums
(defun sht:gnums-of (g gnl / res)
  (foreach p gnl (if (= (car p) g) (setq res (cons (cdr p) res))))
  (reverse res))

;; Следующий свободный номер: наибольший целый + 1
(defun sht:next-num (nums / mx)
  (setq mx 0)
  (foreach s nums
    (if (sht:int-p s) (setq mx (max mx (atoi s)))))
  (itoa (1+ mx)))

;; Есть ли номер s среди nums (без учёта регистра и пробелов)
(defun sht:num-used-p (s nums)
  (setq s (strcase (sht:trim s)))
  (vl-some '(lambda (x) (= (strcase x) s)) nums))

;; Порядок номеров листов: 1 < 1.1 < 1.2 < 1.10 < 1.а < 1.б < 2 < 2.1 < 10.
;; Части через «.»; в части — число, затем буквы (кириллица и латиница — по алфавиту).
(defun sht:tok-key (tok / i n c r)
  (setq i 1 n 0)
  (while (and (<= i (strlen tok)) (wcmatch (setq c (substr tok i 1)) "#"))
    (setq n (+ (* n 10) (atoi c))
          i (1+ i)))
  (setq c (strcase (substr tok i 1) T)
        r (cond ((= c "") 0)
                ((setq r (vl-string-search c *sht:AbcRu*)) (1+ r))
                ((setq r (vl-string-search c *sht:AbcEn*)) (+ 101 r))
                (t 200)))
  (if (> i 1) (list 0 n r) (list 1 0 r)))

(defun sht:num-key (s / res)
  (setq s (sht:trim s))
  (if (= s "")
    (list 9)
    (progn
      (foreach tok (sht:split s ".")
        (setq res (append res (sht:tok-key tok))))
      res)))

(defun sht:key< (a b)
  (cond ((null a) (not (null b)))
        ((null b) nil)
        ((< (car a) (car b)) T)
        ((> (car a) (car b)) nil)
        (t (sht:key< (cdr a) (cdr b)))))

(defun sht:num< (a b) (sht:key< (sht:num-key a) (sht:num-key b)))

(defun sht:sort-nums (nums) (vl-sort nums 'sht:num<))

;; Самое частое значение (при равенстве — встретившееся раньше)
(defun sht:most (vals / cnt best p)
  (foreach v vals
    (if (setq p (assoc v cnt))
      (setq cnt (subst (cons v (1+ (cdr p))) p cnt))
      (setq cnt (append cnt (list (cons v 1))))))
  (setq best (car cnt))
  (foreach p cnt (if (> (cdr p) (cdr best)) (setq best p)))
  (car best))

;; Общие поля сейчас: на листах — самое частое значение; листов нет — словарь чертежа,
;; затем умолчания. Возвращает (значения разные-поля).
(defun sht:common-now (attrs sdat) (sht:fw-now *sht:Common* attrs sdat))

;; Объект — лист SHEETS? (вставка блока SHT_…)
(defun sht:sheet-p (en / ed)
  (and en
       (setq ed (entget en))
       (= (cdr (assoc 0 ed)) "INSERT")
       (sht:parse-bname (cdr (assoc 2 ed)))))

;; Сведения о листе: (запись-формата ориентация форма масштаб точка-вставки)
(defun sht:sheet-info (en / ed p)
  (setq ed (entget en)
        p  (sht:parse-bname (cdr (assoc 2 ed))))
  (if p
    (list (car p) (cadr p) (caddr p) (cond ((cdr (assoc 41 ed))) (1.0)) (cdr (assoc 10 ed)))))

;; Атрибут на слое листа и толщиной 0,25 (s0.2: со слоя 0000_Формат он брал 0,5 — «жирный»)
(defun sht:att-norm (a tag)
  (vl-catch-all-apply 'vla-put-Layer (list a (if (= tag "PNUM") *sht:LayFmtP* *sht:LayFmt*)))
  (vl-catch-all-apply 'vla-put-Lineweight (list a *sht:LwText*)))

;; Записать значение атрибута и вписать его в ячейку (tab — таблица атрибутов формы)
(defun sht:att-set (a val sc tab / at)
  (vla-put-TextString a val)
  (if (setq at (assoc (strcase (vla-get-TagString a)) tab))
    (sht:att-fit a at sc)))

;; Сколько строк займёт текст s высотой h в ширину w (перенос по словам, "\P" — новая строка)
(defun sht:wrap-n (s h w / n line cand)
  (setq n 0)
  (foreach para (sht:split s "\\P")
    (setq line ""
          n    (1+ n))
    (foreach wd (sht:split para " ")
      (setq cand (if (= line "") wd (strcat line " " wd)))
      (if (and (/= line "") (> (sht:str-w cand h) w))
        (setq n    (1+ n)
              line wd)
        (setq line cand))))
  (max n 1))

;; Вписать атрибут в ячейку (s0.2):
;;  однострочный — сжать по ширине до 0,5; не хватило — уменьшить высоту (не ниже 1,8 мм листа);
;;  многострочный — ширина переноса = ширине ячейки, высота 3,5 -> 2,5 -> 1,8, чтобы строки
;;  поместились в высоту ячейки (с зазором 1 мм).
(defun sht:att-fit (a at sc / s h w ch ml need wf hh done)
  (setq s  (vla-get-TextString a)
        h  (* (nth 6 at) sc)
        w  (* (nth 10 at) sc)
        ch (* (nth 13 at) sc)
        ml (vl-catch-all-apply 'vla-get-MTextAttribute (list a)))
  (setq ml (and (nth 11 at) (not (vl-catch-all-error-p ml)) (= ml :vlax-true)))
  (if ml
    (progn
      (vl-catch-all-apply 'vla-put-MTextBoundaryWidth (list a w))
      (foreach hh (list h (* 2.5 sc) (* *sht:MinH* sc))
        (if (and (not done) (<= hh h)
                 (<= (* hh (+ 1.0 (* *sht:LineSp* (1- (sht:wrap-n s hh w))))) (- ch sc)))
          (setq done hh)))
      (vl-catch-all-apply 'vla-put-Height (list a (cond (done) ((* *sht:MinH* sc)))))
      (vl-catch-all-apply 'vla-put-MTextBoundaryWidth (list a w)))
    (progn
      (setq need (apply 'max (cons 0.0 (mapcar '(lambda (x) (sht:str-w x h)) (sht:split s "\\P"))))
            wf   (if (> need w) (/ w need) 1.0)
            hh   h)
      (if (< wf *sht:MinWf*)
        (setq hh (max (* *sht:MinH* sc) (* h (/ wf *sht:MinWf*)))
              wf *sht:MinWf*))
      (vl-catch-all-apply 'vla-put-Height (list a hh))
      (vl-catch-all-apply 'vla-put-ScaleFactor (list a wf)))))

;; Вписать все атрибуты листа (и слой, толщина)
(defun sht:fit-sheet (en / inf tab sc tag at)
  (if (setq inf (sht:sheet-info en))
    (progn
      (setq tab (sht:attr-tab (caddr inf))
            sc  (cadddr inf))
      (foreach a (sht:att-objs en)
        (setq tag (strcase (vla-get-TagString a)))
        (sht:att-norm a tag)
        (if (setq at (assoc tag tab))
          (sht:att-fit a at sc))))))

(defun sht:fit-all ( / n)
  (setq n 0)
  (foreach en (sht:sheets)
    (sht:fit-sheet en)
    (setq n (1+ n)))
  n)

;; Записать изменённые общие поля во все листы. changed — (("SHIFR" . "…") …)
(defun sht:apply-common (changed ens / n p inf)
  (setq n 0)
  (if changed
    (foreach en ens
      (setq inf (sht:sheet-info en)
            n   (1+ n))
      (foreach a (sht:att-objs en)
        (if (setq p (assoc (strcase (vla-get-TagString a)) changed))
          (sht:att-set a (cdr p) (cadddr inf) (sht:attr-tab (caddr inf)))))))
  (if (assoc "STAGE" changed) (sht:stage-layer (cdr (assoc "STAGE" changed))))
  n)

;; Вставить лист: rec orient form — формат и штамп, pt — левый нижний угол листа, sc — масштаб,
;; vals — значения атрибутов. Возвращает ename вставки.
(defun sht:insert (rec orient form pt sc vals / name ins tag p en)
  (setq vals (sht:alist-put (sht:alist-put vals "FORMAT" (sht:fmt-label rec)) "ORIENT" (sht:orient-name orient))
        name (sht:block-ensure rec orient form)
        ins  (vla-InsertBlock (sht:ms) (vlax-3d-point pt) name sc sc sc 0.0))
  (vla-put-Layer ins *sht:LayFmt*)
  (foreach a (vlax-invoke ins 'GetAttributes)
    (setq tag (strcase (vla-get-TagString a)))
    (if (setq p (assoc tag vals))
      (vla-put-TextString a (cdr p))))
  (setq en (vlax-vla-object->ename ins))
  (sht:fit-sheet en)
  en)

;; Заменить лист другим форматом / ориентацией / штампом / масштабом на том же месте
;; (левый нижний угол). Значения: vals (общие поля) <- прежние атрибуты листа <- new (лист, наименование).
(defun sht:replace (en rec orient form sc vals new / inf old)
  (setq inf (sht:sheet-info en)
        old (sht:attrs en))
  (foreach p old (setq vals (sht:alist-put vals (car p) (cdr p))))
  (foreach p new (setq vals (sht:alist-put vals (car p) (cdr p))))
  (setq new (sht:insert rec orient form (nth 4 inf) sc vals))
  (entdel en)
  new)

;;; --------------------------------------------------------------------------
;;;  9. ОКНА (DCL)
;;; --------------------------------------------------------------------------

(defun sht:dcl-lines ()
  (list
    "sht_sheet : dialog {"
    (strcat "  label = \"Лист (SHEETS " *sht:Version* ")\";")
    "  : text { key = \"sht_Info\"; width = 72; }"
    "  : boxed_column {"
    "    label = \"Формат\";"
    "    : row {"
    "      : popup_list { key = \"sht_Fmt\"; label = \"Формат\"; width = 22; }"
    "      : popup_list { key = \"sht_Mult\"; label = \"Кратность\"; width = 24; }"
    "    }"
    "    : radio_row {"
    "      key = \"sht_Or\";"
    "      : radio_button { key = \"sht_OrL\"; label = \"Горизонтальный\"; }"
    "      : radio_button { key = \"sht_OrP\"; label = \"Вертикальный\"; }"
    "    }"
    "    : popup_list { key = \"sht_Form\"; label = \"Штамп\"; width = 66; }"
    "    : toggle { key = \"sht_Side\"; label = \"Боковой штамп (поле подшивки: инв. № подл., подп. и дата, взам. инв. №, согласовано)\"; }"
    "    : text { key = \"sht_Size\"; width = 72; }"
    "  }"
    "  : boxed_column {"
    "    label = \"Лист\";"
    "    : row {"
    "      : edit_box { key = \"sht_Scale\"; label = \"Масштаб 1:\"; edit_width = 8; }"
    "      : edit_box { key = \"sht_Sheet\"; label = \"Лист №\"; edit_width = 8; }"
    "    }"
    "    : edit_box { key = \"sht_Obozn\"; label = \"Обозначение документа (гр. 1; формы 4 и 5)\"; edit_width = 40; edit_limit = 250; }"
    "    : edit_box { key = \"sht_Title\"; label = \"Наименование (гр. 4; у форм 4 и 5 - гр. 5)\"; edit_width = 56; edit_limit = 250; }"
    "  }"
    "  : row {"
    "    : button { key = \"sht_Data\"; label = \"Данные комплекта...\"; width = 28; fixed_width = true; }"
    "    : text { key = \"sht_DataInfo\"; width = 44; }"
    "  }"
    "  : row {"
    "    : button { key = \"sht_SideB\"; label = \"Данные бокового штампа...\"; width = 28; fixed_width = true; }"
    "    : text { key = \"sht_SideInfo\"; width = 44; }"
    "  }"
    "  : row {"
    "    : button { key = \"sht_Attr\"; label = \"Все поля штампа...\"; width = 28; fixed_width = true; }"
    "    : text { key = \"sht_AttrInfo\"; width = 44; }"
    "  }"
    "  errtile;"
    "  ok_cancel;"
    "}"
    ""
    "sht_data : dialog {"
    "  label = \"Штамп - основная надпись\";"
    "  : text { key = \"sht_DataNote\"; width = 100; }"
    "  : text { key = \"sht_DataDiff\"; width = 100; }"
    "  : row {"
    "    : column {"
    "      fixed_width = true;"
    "      : row { fixed_width = true; : edit_box { key = \"sht_FC4IZM\"; width = 4; edit_width = 4; fixed_width = true; edit_limit = 10; } : edit_box { key = \"sht_FC4KOL\"; width = 6; edit_width = 6; fixed_width = true; edit_limit = 10; } : edit_box { key = \"sht_FC4LST\"; width = 6; edit_width = 6; fixed_width = true; edit_limit = 10; } : edit_box { key = \"sht_FC4DOC\"; width = 6; edit_width = 6; fixed_width = true; edit_limit = 20; } : edit_box { width = 8; edit_width = 8; fixed_width = true; is_enabled = false; } : edit_box { key = \"sht_FC4DAT\"; width = 6; edit_width = 6; fixed_width = true; edit_limit = 20; } }"
    "      : row { fixed_width = true; : edit_box { key = \"sht_FC3IZM\"; width = 4; edit_width = 4; fixed_width = true; edit_limit = 10; } : edit_box { key = \"sht_FC3KOL\"; width = 6; edit_width = 6; fixed_width = true; edit_limit = 10; } : edit_box { key = \"sht_FC3LST\"; width = 6; edit_width = 6; fixed_width = true; edit_limit = 10; } : edit_box { key = \"sht_FC3DOC\"; width = 6; edit_width = 6; fixed_width = true; edit_limit = 20; } : edit_box { width = 8; edit_width = 8; fixed_width = true; is_enabled = false; } : edit_box { key = \"sht_FC3DAT\"; width = 6; edit_width = 6; fixed_width = true; edit_limit = 20; } }"
    "      : row { fixed_width = true; : edit_box { key = \"sht_FC2IZM\"; width = 4; edit_width = 4; fixed_width = true; edit_limit = 10; } : edit_box { key = \"sht_FC2KOL\"; width = 6; edit_width = 6; fixed_width = true; edit_limit = 10; } : edit_box { key = \"sht_FC2LST\"; width = 6; edit_width = 6; fixed_width = true; edit_limit = 10; } : edit_box { key = \"sht_FC2DOC\"; width = 6; edit_width = 6; fixed_width = true; edit_limit = 20; } : edit_box { width = 8; edit_width = 8; fixed_width = true; is_enabled = false; } : edit_box { key = \"sht_FC2DAT\"; width = 6; edit_width = 6; fixed_width = true; edit_limit = 20; } }"
    "      : row { fixed_width = true; : edit_box { key = \"sht_FC1IZM\"; width = 4; edit_width = 4; fixed_width = true; edit_limit = 10; } : edit_box { key = \"sht_FC1KOL\"; width = 6; edit_width = 6; fixed_width = true; edit_limit = 10; } : edit_box { key = \"sht_FC1LST\"; width = 6; edit_width = 6; fixed_width = true; edit_limit = 10; } : edit_box { key = \"sht_FC1DOC\"; width = 6; edit_width = 6; fixed_width = true; edit_limit = 20; } : edit_box { width = 8; edit_width = 8; fixed_width = true; is_enabled = false; } : edit_box { key = \"sht_FC1DAT\"; width = 6; edit_width = 6; fixed_width = true; edit_limit = 20; } }"
    "      : row { fixed_width = true; : text { label = \"Изм.\"; width = 4; fixed_width = true; } : text { label = \"Кол.уч.\"; width = 6; fixed_width = true; } : text { label = \"Лист\"; width = 6; fixed_width = true; } : text { label = \"№ док.\"; width = 6; fixed_width = true; } : text { label = \"Подп.\"; width = 8; fixed_width = true; } : text { label = \"Дата\"; width = 6; fixed_width = true; } }"
    "      : row { fixed_width = true; : edit_box { key = \"sht_ROLE1\"; width = 10; edit_width = 10; fixed_width = true; edit_limit = 60; } : edit_box { key = \"sht_NAME1\"; width = 12; edit_width = 12; fixed_width = true; edit_limit = 60; } : edit_box { width = 8; edit_width = 8; fixed_width = true; is_enabled = false; } : edit_box { key = \"sht_DATE1\"; width = 6; edit_width = 6; fixed_width = true; edit_limit = 20; } }"
    "      : row { fixed_width = true; : edit_box { key = \"sht_ROLE2\"; width = 10; edit_width = 10; fixed_width = true; edit_limit = 60; } : edit_box { key = \"sht_NAME2\"; width = 12; edit_width = 12; fixed_width = true; edit_limit = 60; } : edit_box { width = 8; edit_width = 8; fixed_width = true; is_enabled = false; } : edit_box { key = \"sht_DATE2\"; width = 6; edit_width = 6; fixed_width = true; edit_limit = 20; } }"
    "      : row { fixed_width = true; : edit_box { key = \"sht_ROLE3\"; width = 10; edit_width = 10; fixed_width = true; edit_limit = 60; } : edit_box { key = \"sht_NAME3\"; width = 12; edit_width = 12; fixed_width = true; edit_limit = 60; } : edit_box { width = 8; edit_width = 8; fixed_width = true; is_enabled = false; } : edit_box { key = \"sht_DATE3\"; width = 6; edit_width = 6; fixed_width = true; edit_limit = 20; } }"
    "      : row { fixed_width = true; : edit_box { key = \"sht_ROLE4\"; width = 10; edit_width = 10; fixed_width = true; edit_limit = 60; } : edit_box { key = \"sht_NAME4\"; width = 12; edit_width = 12; fixed_width = true; edit_limit = 60; } : edit_box { width = 8; edit_width = 8; fixed_width = true; is_enabled = false; } : edit_box { key = \"sht_DATE4\"; width = 6; edit_width = 6; fixed_width = true; edit_limit = 20; } }"
    "      : row { fixed_width = true; : edit_box { key = \"sht_ROLE5\"; width = 10; edit_width = 10; fixed_width = true; edit_limit = 60; } : edit_box { key = \"sht_NAME5\"; width = 12; edit_width = 12; fixed_width = true; edit_limit = 60; } : edit_box { width = 8; edit_width = 8; fixed_width = true; is_enabled = false; } : edit_box { key = \"sht_DATE5\"; width = 6; edit_width = 6; fixed_width = true; edit_limit = 20; } }"
    "      : row { fixed_width = true; : edit_box { key = \"sht_ROLE6\"; width = 10; edit_width = 10; fixed_width = true; edit_limit = 60; } : edit_box { key = \"sht_NAME6\"; width = 12; edit_width = 12; fixed_width = true; edit_limit = 60; } : edit_box { width = 8; edit_width = 8; fixed_width = true; is_enabled = false; } : edit_box { key = \"sht_DATE6\"; width = 6; edit_width = 6; fixed_width = true; edit_limit = 20; } }"
    "    }"
    "    : column {"
    "      : text { key = \"sht_FG1Tx\"; width = 66; }"
    "      : edit_box { key = \"sht_SHIFR\"; width = 66; edit_width = 66; fixed_width = true; edit_limit = 250; }"
    "      : text { label = \"Объект (гр. 2)\"; width = 66; }"
    "      : edit_box { key = \"sht_OBJECT\"; width = 66; edit_width = 66; fixed_width = true; edit_limit = 250; }"
    "      : row {"
    "        : column { : text { label = \"Здание, сооружение (гр. 3)\"; width = 38; fixed_width = true; } : edit_box { key = \"sht_BUILDING\"; width = 38; edit_width = 38; fixed_width = true; edit_limit = 250; } }"
    "        : column {"
    "          : row { fixed_width = true; : text { label = \"Стадия\"; width = 8; fixed_width = true; } : text { label = \"Лист\"; width = 8; fixed_width = true; } : text { label = \"Листов\"; width = 10; fixed_width = true; } }"
    "          : row { fixed_width = true; : edit_box { key = \"sht_STAGE\"; width = 8; edit_width = 8; fixed_width = true; edit_limit = 10; } : edit_box { key = \"sht_FSHEET\"; width = 8; edit_width = 8; fixed_width = true; edit_limit = 20; } : edit_box { key = \"sht_FSHEETS\"; width = 10; edit_width = 10; fixed_width = true; edit_limit = 20; } }"
    "        }"
    "      }"
    "      : row {"
    "        : column { : text { key = \"sht_FTitleTx\"; width = 38; fixed_width = true; } : edit_box { key = \"sht_FTITLE\"; width = 38; edit_width = 38; fixed_width = true; edit_limit = 250; } }"
    "        : column { : text { label = \"Организация (гр. 9)\"; width = 28; fixed_width = true; } : edit_box { key = \"sht_ORG\"; width = 28; edit_width = 28; fixed_width = true; edit_limit = 250; } }"
    "      }"
    "    }"
    "  }"
    "  : boxed_row {"
    "    label = \"Только у формы 4 (чертежи строительных изделий)\";"
    "    : edit_box { key = \"sht_FMASS\"; label = \"Масса (гр. 24)\"; edit_width = 8; edit_limit = 20; }"
    "    : edit_box { key = \"sht_FSCALE\"; label = \"Масштаб (гр. 25)\"; edit_width = 8; edit_limit = 20; }"
    "    : edit_box { key = \"sht_FMATER\"; label = \"Материал (гр. 23)\"; edit_width = 30; edit_limit = 250; }"
    "  }"
    "  : text { key = \"sht_FMsg\"; width = 100; }"
    "  errtile;"
    "  : row {"
    "    : button { key = \"sht_TplLoad\"; label = \"Выбрать шаблон...\"; width = 20; fixed_width = true; }"
    "    : button { key = \"sht_TplSave\"; label = \"Сохранить шаблон...\"; width = 20; fixed_width = true; }"
    "    : spacer { width = 1; }"
    "    : button { key = \"sht_One\"; label = \"Для этого листа\"; width = 18; fixed_width = true; }"
    "    : button { key = \"accept\"; label = \"Для всех листов\"; width = 18; fixed_width = true; is_default = true; }"
    "    : button { key = \"cancel\"; label = \"Отмена\"; width = 12; fixed_width = true; is_cancel = true; }"
    "  }"
    "}"
    ""
    "sht_side : dialog {"
    "  label = \"Боковой штамп - поле подшивки\";"
    "  : text { key = \"sht_DataNote\"; width = 100; }"
    "  : text { key = \"sht_DataDiff\"; width = 100; }"
    "  : boxed_column {"
    "    label = \"Согласовано\";"
    "    : row { fixed_width = true; : text { label = \"Должность\"; width = 16; fixed_width = true; } : text { label = \"Фамилия\"; width = 22; fixed_width = true; } : text { label = \"Дата\"; width = 9; fixed_width = true; } }"
    "    : row { fixed_width = true; : edit_box { key = \"sht_SOGL1R\"; width = 16; edit_width = 16; fixed_width = true; edit_limit = 60; } : edit_box { key = \"sht_SOGL1N\"; width = 22; edit_width = 22; fixed_width = true; edit_limit = 60; } : edit_box { key = \"sht_SOGL1D\"; width = 9; edit_width = 9; fixed_width = true; edit_limit = 20; } }"
    "    : row { fixed_width = true; : edit_box { key = \"sht_SOGL2R\"; width = 16; edit_width = 16; fixed_width = true; edit_limit = 60; } : edit_box { key = \"sht_SOGL2N\"; width = 22; edit_width = 22; fixed_width = true; edit_limit = 60; } : edit_box { key = \"sht_SOGL2D\"; width = 9; edit_width = 9; fixed_width = true; edit_limit = 20; } }"
    "  }"
    "  : boxed_row {"
    "    label = \"Инвентарные номера\";"
    "    : edit_box { key = \"sht_VZAM\"; label = \"Взам. инв. № (гр. 22)\"; edit_width = 14; edit_limit = 40; }"
    "    : edit_box { key = \"sht_INV\"; label = \"Инв. № подл. (гр. 20)\"; edit_width = 14; edit_limit = 40; }"
    "  }"
    "  : text { key = \"sht_FMsg\"; width = 100; }"
    "  errtile;"
    "  : row {"
    "    : button { key = \"sht_TplLoad\"; label = \"Выбрать шаблон...\"; width = 20; fixed_width = true; }"
    "    : button { key = \"sht_TplSave\"; label = \"Сохранить шаблон...\"; width = 20; fixed_width = true; }"
    "    : spacer { width = 1; }"
    "    : button { key = \"sht_One\"; label = \"Для этого листа\"; width = 18; fixed_width = true; }"
    "    : button { key = \"accept\"; label = \"Для всех листов\"; width = 18; fixed_width = true; is_default = true; }"
    "    : button { key = \"cancel\"; label = \"Отмена\"; width = 12; fixed_width = true; is_cancel = true; }"
    "  }"
    "}"
    ""
    "sht_tpl : dialog {"
    "  label = \"Шаблоны данных комплекта\";"
    "  : text { key = \"sht_TDir\"; width = 80; }"
    "  : list_box { key = \"sht_TList\"; width = 80; height = 10; }"
    "  : edit_box { key = \"sht_TName\"; label = \"Имя шаблона\"; edit_width = 50; edit_limit = 100; }"
    "  : text { key = \"sht_TInfo\"; width = 80; }"
    "  : text { key = \"sht_TInfo2\"; width = 80; }"
    "  : text { label = \"В шаблоне: шифр, объект, стадия, организация, должности и фамилии, согласовано (без дат).\"; }"
    "  errtile;"
    "  : row {"
    "    : button { key = \"sht_TDirB\"; label = \"Папка...\"; width = 12; fixed_width = true; }"
    "    : button { key = \"sht_TDel\"; label = \"Удалить\"; width = 12; fixed_width = true; }"
    "    : spacer { width = 1; }"
    "    : button { key = \"sht_TUse\"; label = \"Подставить\"; width = 14; fixed_width = true; is_default = true; }"
    "    : button { key = \"sht_TSave\"; label = \"Сохранить\"; width = 14; fixed_width = true; }"
    "    : button { key = \"cancel\"; label = \"Отмена\"; width = 12; fixed_width = true; is_cancel = true; }"
    "  }"
    "}"
    ""
    "sht_plot : dialog {"
    (strcat "  label = \"Печать в PDF (SHEETS " *sht:Version* ")\";")
    "  : boxed_column {"
    "    label = \"Листы - по порядку номеров (щелчок отмечает / снимает)\";"
    "    : list_box { key = \"sht_PList\"; multiple_select = true; width = 90; height = 16; tabs = \"8 22 31\"; }"
    "    : row {"
    "      : button { key = \"sht_PAll\"; label = \"Все\"; width = 10; fixed_width = true; }"
    "      : button { key = \"sht_PNone\"; label = \"Ни одного\"; width = 12; fixed_width = true; }"
    "      : button { key = \"sht_PSel\"; label = \"Выбрать в чертеже <\"; width = 22; fixed_width = true; }"
    "      : edit_box { key = \"sht_PNums\"; label = \"Номера:\"; edit_width = 16; edit_limit = 250; }"
    "      : button { key = \"sht_PNumsGo\"; label = \"Отметить\"; width = 12; fixed_width = true; is_default = true; }"
    "    }"
    "    : text { key = \"sht_PCount\"; width = 90; }"
    "    : text { key = \"sht_POff\"; width = 90; }"
    "  }"
    "  : boxed_radio_row {"
    "    key = \"sht_PMode\";"
    "    label = \"Вывод\";"
    "    : radio_button { key = \"sht_PModeAll\"; label = \"Один PDF - весь комплект\"; }"
    "    : radio_button { key = \"sht_PModeOne\"; label = \"Отдельный PDF на каждый лист\"; }"
    "  }"
    "  : boxed_column {"
    "    label = \"Куда\";"
    "    : row {"
    "      : edit_box { key = \"sht_PDir\"; label = \"Папка\"; edit_width = 70; edit_limit = 250; }"
    "      : button { key = \"sht_PDirB\"; label = \"...\"; width = 6; fixed_width = true; }"
    "    }"
    "    : text { key = \"sht_PFile\"; width = 90; }"
    "  }"
    "  : popup_list { key = \"sht_PCtb\"; label = \"Стиль печати\"; width = 50; }"
    "  : toggle { key = \"sht_PSave\"; label = \"Сохранить чертёж перед печатью одним PDF\"; }"
    "  : toggle { key = \"sht_POpen\"; label = \"Открыть результат после печати\"; }"
    "  errtile;"
    "  : row {"
    "    : button { key = \"accept\"; label = \"Печать\"; width = 14; fixed_width = true; }"
    "    cancel_button;"
    "  }"
    "}"
    ""
    "sht_list : dialog {"
    (strcat "  label = \"Ведомость рабочих чертежей (SHEETS " *sht:Version* ")\";")
    "  : boxed_column {"
    "    label = \"Строки ведомости - листы с номером, по порядку номеров\";"
    "    : list_box { key = \"sht_LList\"; width = 100; height = 16; tabs = \"8 80\"; }"
    "    : text { key = \"sht_LInfo\"; width = 100; }"
    "    : text { key = \"sht_LOff\"; width = 100; }"
    "  }"
    "  : edit_box { key = \"sht_LTitle\"; label = \"Заголовок\"; edit_width = 64; edit_limit = 250; }"
    "  : toggle { key = \"sht_LCnt\"; label = \"Графа «Листов» - число листов на первом листе (на остальных пусто)\"; }"
    "  : toggle { key = \"sht_LAuto\"; label = \"Обновлять автоматически (и ведомость спецификаций): при сохранении и печати, после команд SHEETS\"; }"
    "  errtile;"
    "  : row {"
    "    : button { key = \"sht_LIns\"; label = \"Вставить ведомость <\"; width = 24; fixed_width = true; }"
    "    : button { key = \"accept\"; label = \"Обновить\"; width = 14; fixed_width = true; is_default = true; }"
    "    cancel_button;"
    "  }"
    "}"
    ""
    "sht_spec : dialog {"
    (strcat "  label = \"Ведомость спецификаций (SHEETS " *sht:Version* ")\";")
    "  : boxed_column {"
    "    label = \"Строки ведомости - таблицы со словом «Спецификация» в заголовке, на листах с номером\";"
    "    : list_box { key = \"sht_SList\"; width = 100; height = 12; tabs = \"8 80\"; }"
    "    : text { key = \"sht_SInfo\"; width = 100; }"
    "  }"
    "  : boxed_column {"
    "    label = \"Не войдут: не на листе SHEETS формы 3, на листе без номера, на листе бумаги\";"
    "    : list_box { key = \"sht_SOff\"; width = 100; height = 4; tabs = \"8 80\"; }"
    "  }"
    "  : edit_box { key = \"sht_STitle\"; label = \"Заголовок\"; edit_width = 64; edit_limit = 250; }"
    "  : toggle { key = \"sht_SAuto\"; label = \"Обновлять автоматически (и ведомость листов): при сохранении и печати, после команд SHEETS\"; }"
    "  errtile;"
    "  : row {"
    "    : button { key = \"sht_SIns\"; label = \"Вставить ведомость <\"; width = 24; fixed_width = true; }"
    "    : button { key = \"accept\"; label = \"Обновить\"; width = 14; fixed_width = true; is_default = true; }"
    "    cancel_button;"
    "  }"
    "}"
    ""
    "sht_refs : dialog {"
    (strcat "  label = \"Ведомость ссылочных и прилагаемых документов (SHEETS " *sht:Version* ")\";")
    "  : boxed_column {"
    "    label = \"Прилагаемые документы - листы формы 4: обозначение (гр. 1), наименование (гр. 5), листов\";"
    "    : list_box { key = \"sht_RAtt\"; width = 100; height = 7; tabs = \"30 90\"; }"
    "    : text { key = \"sht_RInfo\"; width = 100; }"
    "  }"
    "  : boxed_column {"
    "    label = \"Ссылочные документы - вписываются здесь (щелчок по строке - исправить)\";"
    "    : list_box { key = \"sht_RRef\"; width = 100; height = 7; tabs = \"30 90\"; }"
    "    : row {"
    "      : edit_box { key = \"sht_RObo\"; label = \"Обозначение\"; edit_width = 22; edit_limit = 120; }"
    "      : edit_box { key = \"sht_RNam\"; label = \"Наименование\"; edit_width = 44; edit_limit = 250; }"
    "    }"
    "    : row {"
    "      : edit_box { key = \"sht_RNote\"; label = \"Примечание\"; edit_width = 16; edit_limit = 60; }"
    "      : button { key = \"sht_RAdd\"; label = \"Добавить\"; width = 12; fixed_width = true; is_default = true; }"
    "      : button { key = \"sht_RChg\"; label = \"Заменить\"; width = 12; fixed_width = true; }"
    "      : button { key = \"sht_RDel\"; label = \"Удалить\"; width = 12; fixed_width = true; }"
    "      : button { key = \"sht_RUp\"; label = \"Выше\"; width = 10; fixed_width = true; }"
    "      : button { key = \"sht_RDn\"; label = \"Ниже\"; width = 10; fixed_width = true; }"
    "    }"
    "  }"
    "  : edit_box { key = \"sht_RTitle\"; label = \"Заголовок\"; edit_width = 64; edit_limit = 250; }"
    "  : toggle { key = \"sht_RAuto\"; label = \"Обновлять автоматически (все ведомости): при сохранении и печати, после команд SHEETS\"; }"
    "  errtile;"
    "  : row {"
    "    : button { key = \"sht_RIns\"; label = \"Вставить ведомость <\"; width = 24; fixed_width = true; }"
    "    : button { key = \"accept\"; label = \"Обновить\"; width = 14; fixed_width = true; }"
    "    cancel_button;"
    "  }"
    "}"
    ""
    "sht_sign : dialog {"
    (strcat "  label = \"Подписи и логотип (SHEETS " *sht:Version* ")\";")
    "  : boxed_column {"
    "    label = \"Подписи - блок в графу «Подп.» напротив фамилии, на всех листах с основной надписью\";"
    "    : list_box { key = \"sht_GList\"; width = 96; height = 8; tabs = \"34 76\"; }"
    "    : row {"
    "      : popup_list { key = \"sht_GBlk\"; label = \"Блок подписи\"; width = 66; }"
    "      : button { key = \"sht_GFile\"; label = \"Из файла DWG...\"; width = 20; fixed_width = true; }"
    "    }"
    "    : radio_row {"
    "      key = \"sht_GFit\";"
    "      : radio_button { key = \"sht_GFit1\"; label = \"Вписать в графу (15 x 5)\"; }"
    "      : radio_button { key = \"sht_GFit0\"; label = \"Как нарисована (1 ед. блока = 1 мм листа)\"; }"
    "    }"
    "    : text { key = \"sht_GInfo\"; width = 96; }"
    "  }"
    "  : boxed_column {"
    "    label = \"Логотип - в графу 9 (организация), на всех листах с основной надписью\";"
    "    : radio_row {"
    "      key = \"sht_LgKind\";"
    "      : radio_button { key = \"sht_LgKindN\"; label = \"Нет\"; }"
    "      : radio_button { key = \"sht_LgKindB\"; label = \"Блок\"; }"
    "      : radio_button { key = \"sht_LgKindI\"; label = \"Картинка\"; }"
    "    }"
    "    : row {"
    "      : popup_list { key = \"sht_LgBlk\"; label = \"Блок\"; width = 66; }"
    "      : button { key = \"sht_LgBFile\"; label = \"Из файла DWG...\"; width = 20; fixed_width = true; }"
    "    }"
    "    : row {"
    "      : edit_box { key = \"sht_LgPath\"; label = \"Картинка\"; edit_width = 64; edit_limit = 250; }"
    "      : button { key = \"sht_LgBrowse\"; label = \"...\"; width = 6; fixed_width = true; }"
    "    }"
    "    : radio_row {"
    "      key = \"sht_LgFit\";"
    "      : radio_button { key = \"sht_LgFit1\"; label = \"Вписать в графу (50 x 15)\"; }"
    "      : radio_button { key = \"sht_LgFit0\"; label = \"Как нарисован (блок; 1 ед. = 1 мм листа)\"; }"
    "    }"
    "  }"
    "  : text { key = \"sht_GNote\"; width = 96; }"
    "  errtile;"
    "  : row {"
    "    : button { key = \"accept\"; label = \"Расставить\"; width = 14; fixed_width = true; is_default = true; }"
    "    cancel_button;"
    "  }"
    "}"
    "sht_main : dialog {"
    (strcat "  label = \"SHEETS " *sht:Version* " - все команды\";")
    "  : text { key = \"sht_MInfo1\"; width = 100; }"
    "  : text { key = \"sht_MInfo2\"; width = 100; }"
    "  : row {"
    "    : boxed_column {"
    "      label = \"Листы\";"
    "      : button { key = \"sht_MNew\"; label = \"Новый лист...\"; width = 36; fixed_width = true; }"
    "      : button { key = \"sht_MEdit\"; label = \"Изменить лист <\"; width = 36; fixed_width = true; }"
    "      : button { key = \"sht_MData\"; label = \"Данные комплекта...\"; width = 36; fixed_width = true; }"
    "      : button { key = \"sht_MSide\"; label = \"Данные бокового штампа...\"; width = 36; fixed_width = true; }"
    "      : button { key = \"sht_MStamp\"; label = \"Все поля штампа <\"; width = 36; fixed_width = true; }"
    "      : button { key = \"sht_MUpd\"; label = \"Обновить всё\"; width = 36; fixed_width = true; }"
    "    }"
    "    : boxed_column {"
    "      label = \"Ведомости, подписи, печать\";"
    "      : button { key = \"sht_MList\"; label = \"Ведомость рабочих чертежей...\"; width = 36; fixed_width = true; }"
    "      : button { key = \"sht_MSpec\"; label = \"Ведомость спецификаций...\"; width = 36; fixed_width = true; }"
    "      : button { key = \"sht_MRefs\"; label = \"Ведомость ссылочных документов...\"; width = 36; fixed_width = true; }"
    "      : button { key = \"sht_MSign\"; label = \"Подписи и логотип...\"; width = 36; fixed_width = true; }"
    "      : button { key = \"sht_MPlot\"; label = \"Печать в PDF...\"; width = 36; fixed_width = true; }"
    "    }"
    "  }"
    "  : boxed_column {"
    "    label = \"Настройка\";"
    "    : row {"
    "      : text { key = \"sht_MDblTx\"; width = 62; }"
    "      : button { key = \"sht_MDbl\"; label = \"Вкл./выкл.\"; width = 14; fixed_width = true; }"
    "    }"
    "    : row {"
    "      : text { key = \"sht_MAutoTx\"; width = 62; }"
    "      : button { key = \"sht_MAuto\"; label = \"Вкл./выкл.\"; width = 14; fixed_width = true; }"
    "    }"
    "    : row {"
    "      : text { label = \"Перевести листы СПДС в SHEETS (старые рамки - на выключенный слой)\"; width = 62; }"
    "      : button { key = \"sht_MSpds\"; label = \"Перевести...\"; width = 14; fixed_width = true; }"
    "    }"
    "    : row {"
    "      : text { label = \"Разбор объекта (для перехода с СПДС)\"; width = 62; }"
    "      : button { key = \"sht_MProbe\"; label = \"Разбор <\"; width = 14; fixed_width = true; }"
    "    }"
    "  }"
    "  : row {"
    "    : spacer { width = 1; }"
    "    : button { key = \"cancel\"; label = \"Закрыть\"; width = 14; fixed_width = true; is_cancel = true; is_default = true; }"
    "  }"
    "}"
))

;; Открыть файл на запись с нужной кодировкой (при LISPSYS > 0)
(defun sht:open-w (fn / f sys)
  (setq sys (getvar "LISPSYS"))
  (if (and *sht:DclEncoding* sys (> sys 0))
    (setq f (vl-catch-all-apply 'open (list fn "w" *sht:DclEncoding*))))
  (if (or (null f) (vl-catch-all-error-p f))
    (setq f (open fn "w")))
  f)

(defun sht:write-dcl ( / fn f)
  (setq fn (vl-filename-mktemp "sht" nil ".dcl"))
  (if (setq f (sht:open-w fn))
    (progn
      (foreach s (sht:dcl-lines) (write-line s f))
      (close f)
      fn)))

;; Выгрузить окна и удалить временный файл (dcl_id, dclFile — локальные команды)
(defun sht:dlg-cleanup ()
  (if (and dcl_id (> dcl_id 0))
    (vl-catch-all-apply 'unload_dialog (list dcl_id)))
  (setq dcl_id nil)
  (if (and dclFile (findfile dclFile))
    (vl-file-delete dclFile))
  (setq dclFile nil))

;; Загрузить окна: T — можно открывать
(defun sht:dlg-load ()
  (cond
    ((not (setq dclFile (sht:write-dcl)))
     (princ "\nSHEETS: не удалось записать временный DCL-файл.") nil)
    ((not (and (setq dcl_id (load_dialog dclFile)) (> dcl_id 0)))
     (princ "\nSHEETS: не удалось загрузить окна.") nil)
    (t T)))

;;; --------------------------------------------------------------------------
;;;  10. ЛОГИКА ОКОН
;;;  Рабочие переменные (локальные в командах, видны динамически):
;;;    sht:mode — 'NEW / 'EDIT; sht:fmt sht:mult sht:or sht:form — формат и штамп (форма с "N" —
;;;    без бокового штампа); sht:sc0 sht:no0 sht:title0 sht:obozn0 — масштаб, номер, наименование,
;;;    обозначение (графа 1 форм 4, 5) в начале; sht:sugg — предложенный номер нового листа;
;;;    sht:res — результат окна «Лист» (формат кратность ориентация штамп масштаб номер наименование
;;;    обозначение); sht:cur — общие поля (alist), sht:diff — поля, разные на листах; sht:pend —
;;;    изменённые в окне «Данные комплекта»; sht:gnl — номера других листов по группам нумерации
;;;    (sht:gnums), sht:nsh — листов в чертеже; sht:dres — результат окна данных.
;;; --------------------------------------------------------------------------

(defun sht:set-popup (key items idx)
  (start_list key)
  (mapcar 'add_list items)
  (end_list)
  (set_tile key (itoa (if idx idx 0))))

;; Число из поля ввода (запятая допускается) или nil
(defun sht:tile-num (key / s)
  (setq s (sht:trim (vl-string-translate "," "." (get_tile key))))
  (if (/= s "") (distof s 2)))

;; Список номеров для строки сведений (не длиннее ~60 знаков)
(defun sht:nums-str (nums / s)
  (setq s "")
  (foreach x (sht:sort-nums nums)
    (if (< (strlen s) 60)
      (setq s (strcat s (if (= s "") "" ", ") x))))
  (if (and (> (length nums) 0) (>= (strlen s) 60)) (setq s (strcat s " ...")))
  s)

;; Группа нумерации и номера других листов этой группы — по форме и обозначению в окне (s0.10)
(defun sht:cur-group ()
  (sht:num-group sht:form (if (sht:fdoc-p sht:form) (get_tile "sht_Obozn") "")))
(defun sht:cur-nums () (sht:gnums-of (sht:cur-group) sht:gnl))

(defun sht:new-info ( / nl doc)
  (setq nl  (sht:cur-nums)
        doc (sht:fdoc-p sht:form))
  (set_tile "sht_Info"
    (cond
      ((eq sht:mode 'EDIT)
       (strcat "Изменить лист " (if (= sht:no0 "") "(без номера)" sht:no0)
               (if nl (strcat (if doc ". Другие листы документа: " ". Другие листы: ") (sht:nums-str nl)) "")))
      ((> (length nl) 0)
       (strcat (if doc "Новый лист документа. Листов документа: " "Новый лист. Листов в чертеже: ")
               (itoa (length nl)) ". Номера: " (sht:nums-str nl)))
      (doc "Новый лист. Листов этого документа (графа 1) пока нет.")
      (t "Новый лист. Листов в чертеже пока нет."))))

(defun sht:data-info ( / s st)
  (setq s  (sht:trim (cdr (assoc "SHIFR" sht:cur)))
        st (sht:trim (cdr (assoc "STAGE" sht:cur))))
  (set_tile "sht_DataInfo"
    (strcat (if (= s "") "Шифр не задан" (strcat "Шифр: " s))
            (if (= st "") "" (strcat ", стадия " st))
            (if sht:pend " (изменено)" ""))))

;; Формат выбран: список кратностей, ориентация, размер
(defun sht:on-fmt ( / ms)
  (setq sht:fmt (nth (atoi (get_tile "sht_Fmt")) *sht:FmtNames*)
        ms      (sht:mults sht:fmt))
  (if (not (member sht:mult ms)) (setq sht:mult 1))
  (sht:set-popup "sht_Mult"
    (mapcar '(lambda (m) (if (= m 1) "1 (основной)" (strcat "x" (itoa m)))) ms)
    (vl-position sht:mult ms))
  (sht:on-size))

(defun sht:on-mult ()
  (setq sht:mult (nth (atoi (get_tile "sht_Mult")) (sht:mults sht:fmt)))
  (sht:on-size))

;; Штамп, боковой штамп или обозначение изменили (s0.10): форма, поле обозначения, номер нового листа
;; (у документа формы 4 / 5 — своя нумерация: предложенный номер меняется, если его не правили)
(defun sht:on-form ()
  (setq sht:form (sht:fmake (nth (atoi (get_tile "sht_Form")) *sht:Forms*) (= (get_tile "sht_Side") "1")))
  (mode_tile "sht_Obozn" (if (sht:fdoc-p sht:form) 0 1))
  (if (and (eq sht:mode 'NEW) (= (sht:trim (get_tile "sht_Sheet")) sht:sugg))
    (progn
      (setq sht:sugg (sht:next-num (sht:cur-nums)))
      (set_tile "sht_Sheet" sht:sugg)))
  (sht:new-info)
  (sht:on-size))

(defun sht:on-size ( / rec wh)
  (if (sht:portrait-only-p sht:fmt sht:mult)
    (progn (setq sht:or "P") (mode_tile "sht_OrL" 1))
    (progn
      (mode_tile "sht_OrL" 0)
      (setq sht:or (if (= (get_tile "sht_Or") "sht_OrP") "P" "L"))))
  (set_tile "sht_Or" (if (= sht:or "P") "sht_OrP" "sht_OrL"))
  (setq rec (sht:fmt-rec sht:fmt sht:mult)
        wh  (sht:fmt-wh rec sht:or))
  (set_tile "sht_Size"
    (strcat (sht:fmt-label rec) ": " (sht:n2s (car wh)) " x " (sht:n2s (cadr wh)) " мм"
            (if (= sht:mult 1) "" "  (кратный, бумага - из PMP)")
            "   блок " (sht:bname rec sht:or sht:form))))

(defun sht:sheet-init ()
  (set_tile "sht_Obozn" sht:obozn0)
  (sht:set-popup "sht_Fmt" *sht:FmtNames* (vl-position sht:fmt *sht:FmtNames*))
  (sht:set-popup "sht_Form" *sht:FormNames* (vl-position (sht:fbase sht:form) *sht:Forms*))
  (set_tile "sht_Side" (if (sht:fside-p sht:form) "1" "0"))
  (mode_tile "sht_Obozn" (if (sht:fdoc-p sht:form) 0 1))
  (sht:new-info)
  (set_tile "sht_Or" (if (= sht:or "P") "sht_OrP" "sht_OrL"))
  (sht:on-fmt)
  (set_tile "sht_Scale" (sht:n2s sht:sc0))
  (set_tile "sht_Sheet" sht:no0)
  (set_tile "sht_Title" sht:title0)
  (sht:data-info)
  (if (eq sht:mode 'EDIT)
    (progn
      (set_tile "sht_AttrInfo" "записать окно и открыть штамп этого листа")
      (set_tile "sht_SideInfo" "записать окно и открыть боковой штамп листа"))
    (progn
      (mode_tile "sht_Attr" 1)
      (set_tile "sht_AttrInfo" "")
      (set_tile "sht_SideInfo" "для всех листов")))
  (action_tile "sht_Fmt" "(sht:on-fmt)")
  (action_tile "sht_Mult" "(sht:on-mult)")
  (action_tile "sht_Or" "(sht:on-size)")
  (action_tile "sht_Form" "(sht:on-form)")
  (action_tile "sht_Side" "(sht:on-form)")
  (action_tile "sht_Obozn" "(sht:on-form)")
  (action_tile "sht_Data" "(sht:on-data)")
  (action_tile "sht_Attr" "(sht:sheet-read 3)")
  (action_tile "sht_SideB" (if (eq sht:mode 'EDIT) "(sht:sheet-read 4)" "(sht:on-side)"))
  (action_tile "accept" "(sht:sheet-read 1)"))

;; OK (code 1) / «Все поля штампа...» (code 3) / «Данные бокового штампа...» (code 4): проверить ввод -> sht:res
(defun sht:sheet-read (code / sc no)
  (setq sc (sht:tile-num "sht_Scale")
        no (sht:trim (get_tile "sht_Sheet")))
  (cond
    ((not (and sc (> sc 0)))
     (set_tile "error" "Масштаб: введите число больше 0 (1:100 -> 100)."))
    ((sht:num-used-p no (sht:cur-nums))
     (set_tile "error" (strcat "Лист " no (if (sht:fdoc-p sht:form) " уже есть в этом документе" " уже есть в чертеже")
                               " - укажите другой номер.")))
    (t
     (setq sht:res (list sht:fmt sht:mult sht:or sht:form sc no (sht:trim (get_tile "sht_Title"))
                         (sht:trim (vl-string-translate "|" "/" (get_tile "sht_Obozn")))))
     (done_dialog code))))

;; Окно «Лист» целиком: загрузить, показать, выгрузить. Возвращает код закрытия.
(defun sht:sheet-dialog ( / dcl_id dclFile ret)
  (if (sht:dlg-load)
    (if (new_dialog "sht_sheet" dcl_id)
      (progn
        (sht:sheet-init)
        (setq ret (start_dialog)))
      (princ "\nSHEETS: не удалось открыть окно.")))
  (sht:dlg-cleanup)
  ret)

;; Кнопка «Данные комплекта...»
(defun sht:on-data ( / r)
  (if (setq r (sht:data-dialog sht:cur sht:diff sht:nsh))
    (setq sht:cur  (car r)
          sht:pend (sht:merge-changes sht:pend (cadr r)))
    )
  (sht:data-info))

;; Кнопка «Данные бокового штампа...» нового листа (s0.11) — для всех листов
(defun sht:on-side ( / r)
  (if (setq r (sht:kit-dialog 'SIDE sht:cur sht:diff sht:nsh))
    (setq sht:cur  (car r)
          sht:pend (sht:merge-changes sht:pend (cadr r))))
  (sht:data-info))

;; Добавить новые изменения к прежним (новые важнее)
(defun sht:merge-changes (old new)
  (foreach p new (setq old (sht:alist-put old (car p) (cdr p))))
  old)

;; Окно «Данные комплекта» (s0.11 — в виде штампа): cur — значения, diff — поля, разные на листах,
;; n — листов. Возвращает (новые-значения изменённые) или nil (Отмена).
(defun sht:data-dialog (cur diff n) (sht:kit-dialog 'STAMP cur diff n))

(defun sht:diff-str (diff / s nm)
  (setq s "")
  (foreach tag diff
    (setq nm (cond ((cdr (assoc tag *sht:CommonNames*)))
                   ((wcmatch tag "ROLE#") (strcat "должность " (substr tag 5)))
                   ((wcmatch tag "NAME#") (strcat "фамилия " (substr tag 5)))
                   ((wcmatch tag "DATE#") (strcat "дата " (substr tag 5)))
                   (t "согласовано")))
    (if (not (vl-string-search nm s))
      (setq s (strcat s (if (= s "") "" ", ") nm))))
  s)

;;; --------------------------------------------------------------------------
;;;  10а. ОКНА В ВИДЕ ШТАМПА (s0.11): «Данные комплекта», «Данные бокового штампа», «Все поля штампа»
;;;  Рабочие переменные окна (локальные в sht:fw-dialog): sht:fw-kind — 'STAMP / 'SIDE; sht:fw-form — форма
;;;  листа (nil — данные комплекта); sht:fw-tl — доступные поля ((поле . тег) …); sht:fw-v0 — значения в начале;
;;;  sht:fw-cur — общие поля комплекта (для шаблона); sht:fw-gnl — номера других листов; sht:fw-res — итог.
;;; --------------------------------------------------------------------------

(defun sht:fw-tile (tag) (cdr (assoc tag *sht:FwTiles*)))

;; Строки изменений окна «Штамп» (C4IZM … C1DAT)
(defun sht:chg-tags () (vl-remove-if-not '(lambda (x) (wcmatch x "C#*")) *sht:StampTags*))

;; Доступные поля окна kind для формы form (nil — комплект: без полей листа): ((поле . тег) …).
;; Поля нет на этой форме — его нет в списке (в окне оно серое). Графа 1 у форм 4, 5 — OBOZN.
(defun sht:fw-map (kind form / tab tg res)
  (setq tab (sht:attr-tab (cond (form) ("3"))))
  (foreach tag (if (eq kind 'SIDE) *sht:SideTags* *sht:StampTags*)
    (setq tg (if (and (= tag "SHIFR") (assoc "OBOZN" tab)) "OBOZN" tag))
    (if (and (assoc tg tab) (or form (not (member tg *sht:OneTags*))))
      (setq res (cons (cons (sht:fw-tile tag) tg) res))))
  (reverse res))

;; Значения полей tags на листах: самое частое; листов (поля) нет — словарь чертежа, затем умолчания.
;; Возвращает (значения разные-поля).
(defun sht:fw-now (tags attrs sdat / res diff vals p)
  (foreach tag tags
    (setq vals nil)
    (foreach a attrs
      (if (setq p (assoc tag a)) (setq vals (cons (cdr p) vals))))
    (setq vals (reverse vals))
    (if (and vals (vl-some '(lambda (v) (/= v (car vals))) vals))
      (setq diff (cons tag diff)))
    (setq res (cons (cons tag
                          (cond (vals (sht:most vals))
                                ((cdr (assoc tag sdat)))
                                ((cdr (assoc tag *sht:CommonDef*)))
                                ("")))
                    res)))
  (list (reverse res) (reverse diff)))

;; Окно-штамп kind ('STAMP — «sht_data», 'SIDE — «sht_side»). form — форма листа (nil — данные комплекта:
;; только «Для всех листов»), v0 — значения ((тег . значение) …), cur — общие поля комплекта (для шаблона),
;; note / diff — строки сведений, gnl — номера других листов (проверка номера).
;; Возвращает (область новые изменённые): 'ONE — в этот лист, 'ALL — во все листы; nil — «Отмена».
(defun sht:fw-dialog (kind form v0 cur note diff gnl / sht:fw-kind sht:fw-form sht:fw-tl sht:fw-v0
                      sht:fw-cur sht:fw-gnl sht:fw-res)
  (setq sht:fw-kind kind
        sht:fw-form form
        sht:fw-v0   v0
        sht:fw-cur  cur
        sht:fw-gnl  gnl
        sht:fw-tl   (sht:fw-map kind form))
  (if (new_dialog (if (eq kind 'SIDE) "sht_side" "sht_data") dcl_id)
    (progn
      (sht:fw-init note diff)
      (start_dialog)))
  sht:fw-res)

(defun sht:fw-init (note diff / k tg g1)
  (foreach tag (if (eq sht:fw-kind 'SIDE) *sht:SideTags* *sht:StampTags*)
    (setq k  (sht:fw-tile tag)
          tg (cdr (assoc k sht:fw-tl)))
    (set_tile k (if tg (cond ((cdr (assoc tg sht:fw-v0))) ("")) ""))
    (if (or (not tg) (= tg "SHEETS")) (mode_tile k 1)))
  (if (eq sht:fw-kind 'STAMP)
    (progn
      (setq g1 (cdr (assoc "sht_SHIFR" sht:fw-tl)))
      (set_tile "sht_FG1Tx" (if (= g1 "OBOZN") "Обозначение документа (гр. 1)" "Обозначение, шифр (гр. 1)"))
      (set_tile "sht_FTitleTx"
        (if (and sht:fw-form (sht:fdoc-p sht:fw-form)) "Наименование (гр. 5)" "Наименование (гр. 4)"))))
  (set_tile "sht_DataNote" note)
  (set_tile "sht_DataDiff" diff)
  (set_tile "sht_FMsg" "")
  (mode_tile "sht_One" (if sht:fw-form 0 1))
  (action_tile "sht_One" "(sht:fw-ok 'ONE)")
  (action_tile "accept" "(sht:fw-ok 'ALL)")
  (action_tile "sht_TplLoad" "(sht:tpl-use)")
  (action_tile "sht_TplSave" "(sht:tpl-save)"))

;; «Для этого листа» / «Для всех листов»: значения доступных полей, изменённые (без «Листов»);
;; номер листа проверяется на повтор в своей группе нумерации (комплект / документ)
(defun sht:fw-ok (scope / new chg v v0 no)
  (foreach p sht:fw-tl
    (if (/= (cdr p) "SHEETS")
      (progn
        (setq v (sht:trim (get_tile (car p))))
        (if (= (cdr p) "OBOZN") (setq v (vl-string-translate "|" "/" v)))
        (setq v0  (sht:trim (cond ((cdr (assoc (cdr p) sht:fw-v0))) ("")))
              new (append new (list (cons (cdr p) v))))
        (if (/= v v0) (setq chg (append chg (list (cons (cdr p) v))))))))
  (setq no (cdr (assoc "SHEET" new)))
  (cond
    ((and no (or (assoc "SHEET" chg) (assoc "OBOZN" chg))
          (sht:num-used-p no (sht:gnums-of (sht:num-group sht:fw-form (cond ((cdr (assoc "OBOZN" new))) ("")))
                                           sht:fw-gnl)))
     (set_tile "error" (strcat "Лист " no (if (sht:fdoc-p sht:fw-form) " уже есть в этом документе" " уже есть в чертеже")
                               " - укажите другой номер.")))
    (t
     (setq sht:fw-res (list scope new chg))
     (done_dialog 1))))

;; Окно данных комплекта (kind 'STAMP / 'SIDE): cur — общие поля, diff — разные на листах, n — листов.
;; Строки изменений — самое частое на листах (во все листы пойдёт только исправленное).
;; Возвращает (общие-поля изменённые) или nil (Отмена).
(defun sht:kit-dialog (kind cur diff n / tags v0 res new)
  (setq tags (if (eq kind 'SIDE) *sht:SideTags* *sht:StampTags*)
        v0   (if (eq kind 'SIDE)
               cur
               (append cur (car (sht:fw-now (sht:chg-tags) (mapcar 'sht:attrs (sht:sheets)) nil))))
        diff (vl-remove-if-not '(lambda (x) (member x tags)) diff))
  (setq res (sht:fw-dialog kind nil v0 cur
              (if (> n 0)
                (strcat "Листов в чертеже: " (itoa n) ". Что исправите здесь - запишется во все листы;"
                        " остальное на листах не тронется."
                        (if (eq kind 'SIDE) "" " Строки изменений - самое частое на листах."))
                "Листов в чертеже пока нет. Данные запомнятся в чертеже и пойдут в новые листы.")
              (if diff (strcat "На листах разное (показано самое частое): " (sht:diff-str diff)) "")
              nil))
  (if res
    (progn
      (setq new cur)
      (foreach p (cadr res)
        (if (member (car p) *sht:Common*) (setq new (sht:alist-put new (car p) (cdr p)))))
      (list new (caddr res)))))

;; Записать итог окна для листа en (s0.11): 'ONE — всё изменённое только в en; 'ALL — поля листа
;; (*sht:OneTags*) — в en, остальное изменённое — во все листы ens и в словарь чертежа (общие поля).
;; Возвращает (полей-в-лист полей-во-все листов).
(defun sht:fw-commit (scope en chg ens sdat / one all inf n q)
  (if (eq scope 'ONE)
    (setq one chg)
    (foreach p chg
      (if (member (car p) *sht:OneTags*)
        (setq one (append one (list p)))
        (setq all (append all (list p))))))
  (if one
    (progn
      (setq inf (sht:sheet-info en))
      (foreach a (sht:att-objs en)
        (if (setq q (assoc (strcase (vla-get-TagString a)) one))
          (sht:att-set a (cdr q) (cadddr inf) (sht:attr-tab (caddr inf)))))))
  (setq n (if all (sht:apply-common all ens) 0))
  (if all
    (progn
      (foreach p all
        (if (member (car p) *sht:Common*) (setq sdat (sht:alist-put sdat (car p) (cdr p)))))
      (sht:set-write sdat)))
  (list (length one) (length all) n))

;; «Все поля штампа» (kind 'STAMP) / «Данные бокового штампа» ('SIDE) для листа en.
;; У листа нет бокового штампа — окно бокового штампа для всех листов.
(defun sht:fw-edit (en kind / doc sdat ens r inf form a0 no res cr lr sr dcl_id dclFile)
  (setq doc  (sht:doc)
        sdat (sht:prepare)
        ens  (sht:sheets)
        r    (sht:common-now (mapcar 'sht:attrs ens) sdat)
        inf  (sht:sheet-info en)
        form (caddr inf)
        a0   (sht:attrs en)
        no   (sht:trim (cond ((cdr (assoc "SHEET" a0))) (""))))
  (if (and (eq kind 'SIDE) (not (sht:fside-p form)))
    (progn
      (princ "\nУ этого листа нет бокового штампа - окно бокового штампа для всех листов.")
      (sht:kit-cmd 'SIDE))
    (progn
      (if (sht:dlg-load)
        (setq res (sht:fw-dialog kind form a0 (car r)
                    (strcat "Лист " (if (= no "") "без номера" no) " (форма " (sht:fbase form) "). "
                            "«Для этого листа» - только в этот лист; «Для всех листов» - исправленное во все листы"
                            " (номер, наименование, обозначение - только в этот).")
                    "" (sht:gnums (vl-remove en ens)))))
      (sht:dlg-cleanup)
      (cond
        ((null res) (princ "\nШтамп листа: без изменений."))
        ((null (caddr res)) (princ "\nШтамп листа: ничего не изменено."))
        (t
         (vla-StartUndoMark doc)
         (setq cr (sht:fw-commit (car res) en (caddr res) ens sdat))
         (setq sr (sht:sign-auto T))              ; фамилии — подписи (s0.7)
         (setq lr (sht:list-auto T))              ; номер, наименование, изменения — ведомости (s0.5)
         (vla-EndUndoMark doc)
         (princ (strcat "\nЛист " (if (= no "") "(без номера)" no) ": "
                        (if (> (car cr) 0) (strcat "в этот лист полей " (itoa (car cr))) "")
                        (if (and (> (car cr) 0) (> (cadr cr) 0)) "; " "")
                        (if (> (cadr cr) 0)
                          (strcat "во все листы (" (itoa (caddr cr)) ") полей " (itoa (cadr cr)))
                          "")
                        "."))
         (if lr (sht:list-msg lr nil))
         (if sr (sht:sign-msg sr nil))))))
  (princ))

;; Данные комплекта (kind 'STAMP) / бокового штампа ('SIDE) — окно для всех листов, запись.
(defun sht:kit-cmd (kind / doc sdat ens r dcl_id dclFile res)
  (sht:dblclick-setup)
  (setq doc  (sht:doc)
        sdat (sht:prepare)
        ens  (sht:sheets)
        r    (sht:common-now (mapcar 'sht:attrs ens) sdat))
  (if (sht:dlg-load)
    (setq res (sht:kit-dialog kind (car r) (cadr r) (length ens))))
  (sht:dlg-cleanup)
  (cond
    ((null res) (princ (if (eq kind 'SIDE) "\nБоковой штамп: без изменений." "\nДанные комплекта: без изменений.")))
    ((null (cadr res)) (princ (if (eq kind 'SIDE) "\nБоковой штамп: ничего не изменено." "\nДанные комплекта: ничего не изменено.")))
    (t (sht:commit-data doc (car res) (cadr res) ens sdat)))
  (princ))

;; --- шаблоны данных комплекта (s0.11): файлы «имя.txt» (поле=значение) в папке шаблонов ---

;; Папка шаблонов: выбранная («Папка...», реестр SHT_TplDir), иначе «Шаблоны» рядом с SHEETS.lsp
;; (если он в путях поддержки), иначе «Документы\SHEETS\Шаблоны»
(defun sht:tpl-dir ( / d lsp)
  (setq d (sht:dir-norm (cond ((getenv "SHT_TplDir")) (""))))
  (cond
    ((/= d "") d)
    ((setq lsp (findfile "SHEETS.lsp")) (strcat (vl-filename-directory lsp) "\\Шаблоны"))
    (t (strcat (sht:dir-norm (cond ((getenv "USERPROFILE")) ("C:"))) "\\Documents\\SHEETS\\Шаблоны"))))

(defun sht:tpl-file (dir nm) (strcat dir "\\" nm ".txt"))

;; Имена шаблонов в папке (по алфавиту)
(defun sht:tpl-names (dir)
  (vl-sort (mapcar 'vl-filename-base (vl-directory-files dir "*.txt" 1))
           '(lambda (a b) (< (sht:lc a) (sht:lc b)))))

;; Прочитать шаблон: ((поле . значение) …) — только поля шаблона
(defun sht:tpl-read (fn / f s i res)
  (if (and fn (findfile fn) (setq f (open fn "r")))
    (progn
      (while (setq s (read-line f))
        (if (and (/= (substr s 1 1) ";") (setq i (vl-string-search "=" s))
                 (member (strcase (sht:trim (substr s 1 i))) *sht:TplTags*))
          (setq res (sht:alist-put res (strcase (sht:trim (substr s 1 i))) (sht:trim (substr s (+ i 2)))))))
      (close f)))
  res)

;; Записать шаблон. T — записан
(defun sht:tpl-write (fn vals / f)
  (if (setq f (open fn "w"))
    (progn
      (write-line "; SHEETS - шаблон данных комплекта: поле=значение" f)
      (foreach tag *sht:TplTags*
        (write-line (strcat tag "=" (cond ((cdr (assoc tag vals))) (""))) f))
      (close f)
      T)))

;; Значения для шаблона из открытого окна-штампа: поле есть в окне — из окна, иначе — данные комплекта
(defun sht:tpl-vals ( / res k)
  (foreach tag *sht:TplTags*
    (setq k (sht:fw-tile tag))
    (setq res (append res (list (cons tag (if (= (cdr (assoc k sht:fw-tl)) tag)
                                             (sht:trim (get_tile k))
                                             (cond ((cdr (assoc tag sht:fw-cur))) (""))))))))
  res)

;; Подставить шаблон в открытое окно-штамп: только поля этого окна. Возвращает число полей.
(defun sht:tpl-apply (vals / n k)
  (setq n 0)
  (foreach p vals
    (setq k (sht:fw-tile (car p)))
    (if (= (cdr (assoc k sht:fw-tl)) (car p))
      (progn
        (set_tile k (cdr p))
        (setq n (1+ n)))))
  n)

;; Кнопки окна-штампа «Выбрать шаблон...» / «Сохранить шаблон...»
(defun sht:tpl-use ( / vals)
  (if (setq vals (sht:tpl-dialog 'USE nil))
    (set_tile "sht_FMsg" (strcat "Шаблон подставлен, полей: " (itoa (sht:tpl-apply vals))
                                 ". Записать - кнопкой «Для ...»."))))

(defun sht:tpl-save ( / nm)
  (if (setq nm (sht:tpl-dialog 'SAVE (sht:tpl-vals)))
    (set_tile "sht_FMsg" (strcat "Шаблон «" nm "» сохранён."))))

;; Окно «Шаблоны»: mode 'USE — выбрать и подставить (итог — значения), 'SAVE — сохранить vals (итог — имя)
(defun sht:tpl-dialog (mode vals / sht:tmode sht:tvals sht:tdir sht:tnames sht:tres sht:tconf)
  (setq sht:tmode mode
        sht:tvals vals
        sht:tdir  (sht:tpl-dir))
  (if (new_dialog "sht_tpl" dcl_id)
    (progn
      (sht:tpl-fill)
      (mode_tile "sht_TName" (if (eq mode 'SAVE) 0 1))
      (mode_tile (if (eq mode 'SAVE) "sht_TUse" "sht_TSave") 1)
      (action_tile "sht_TList" "(sht:tpl-pick)")
      (action_tile "sht_TDirB" "(sht:tpl-browse)")
      (action_tile "sht_TDel" "(sht:tpl-del)")
      (action_tile "sht_TUse" "(sht:tpl-ok)")
      (action_tile "sht_TSave" "(sht:tpl-ok)")
      (start_dialog)))
  sht:tres)

(defun sht:tpl-fill ()
  (setq sht:tnames (sht:tpl-names sht:tdir))
  (start_list "sht_TList")
  (mapcar 'add_list sht:tnames)
  (end_list)
  (set_tile "sht_TDir" (strcat "Папка: " sht:tdir))
  (set_tile "sht_TInfo" (if sht:tnames "" "Шаблонов в этой папке нет."))
  (set_tile "sht_TInfo2" ""))

;; Выбранное имя в списке или nil
(defun sht:tpl-sel ( / s)
  (setq s (get_tile "sht_TList"))
  (if (/= s "") (nth (atoi s) sht:tnames)))

;; Щелчок по шаблону: имя в поле, коротко — что в нём
(defun sht:tpl-pick ( / nm v)
  (if (setq nm (sht:tpl-sel))
    (progn
      (set_tile "sht_TName" nm)
      (setq v (sht:tpl-read (sht:tpl-file sht:tdir nm)))
      (set_tile "sht_TInfo" (strcat "Шифр: " (cond ((cdr (assoc "SHIFR" v))) ("")) ". Организация: "
                                    (cond ((cdr (assoc "ORG" v))) (""))))
      (set_tile "sht_TInfo2" (strcat "Фамилии: "
                                     (sht:join (vl-remove "" (mapcar '(lambda (x) (cond ((cdr (assoc x v))) ("")))
                                                                     '("NAME1" "NAME2" "NAME3" "NAME4" "NAME5" "NAME6")))
                                               ", "))))))

;; «Подставить» / «Сохранить»
(defun sht:tpl-ok ( / nm fn)
  (set_tile "error" "")
  (if (eq sht:tmode 'USE)
    (if (setq nm (sht:tpl-sel))
      (progn
        (setq sht:tres (sht:tpl-read (sht:tpl-file sht:tdir nm)))
        (done_dialog 1))
      (set_tile "error" "Выберите шаблон в списке."))
    (progn
      (setq nm (sht:trim (get_tile "sht_TName"))
            fn (sht:tpl-file sht:tdir nm))
      (cond
        ((= nm "") (set_tile "error" "Впишите имя шаблона."))
        ((vl-some '(lambda (c) (vl-string-search c nm)) '("\\" "/" ":" "*" "?" "\"" "<" ">" "|"))
         (set_tile "error" "В имени нельзя: \\ / : * ? \" < > |"))
        ((and (findfile fn) (/= sht:tconf nm))
         (setq sht:tconf nm)
         (set_tile "error" (strcat "Шаблон «" nm "» уже есть - нажмите «Сохранить» ещё раз, чтобы заменить.")))
        ((not (sht:mkdir sht:tdir))
         (set_tile "error" (strcat "Не удалось создать папку " sht:tdir " - выберите другую («Папка...»).")))
        ((not (sht:tpl-write fn sht:tvals))
         (set_tile "error" (strcat "Не удалось записать " fn)))
        (t
         (setq sht:tres nm)
         (done_dialog 1))))))

;; «Удалить» — выбранный шаблон (второе нажатие подтверждает)
(defun sht:tpl-del ( / nm)
  (set_tile "error" "")
  (cond
    ((not (setq nm (sht:tpl-sel))) (set_tile "error" "Выберите шаблон в списке."))
    ((/= sht:tconf (strcat "-" nm))
     (setq sht:tconf (strcat "-" nm))
     (set_tile "error" (strcat "Удалить шаблон «" nm "»? Нажмите «Удалить» ещё раз.")))
    (t
     (vl-file-delete (sht:tpl-file sht:tdir nm))
     (setq sht:tconf nil)
     (sht:tpl-fill)
     (set_tile "sht_TInfo" (strcat "Шаблон «" nm "» удалён.")))))

;; «Папка...» — выбрать папку шаблонов (запоминается в реестре)
(defun sht:tpl-browse ( / app sh hw f it p)
  (setq app (vlax-get-acad-object)
        sh  (vl-catch-all-apply 'vla-GetInterfaceObject (list app "Shell.Application")))
  (if (and sh (not (vl-catch-all-error-p sh)))
    (progn
      (setq hw (vl-catch-all-apply 'vla-get-HWND (list app))
            f  (vl-catch-all-apply 'vlax-invoke-method
                 (list sh 'BrowseForFolder (if (vl-catch-all-error-p hw) 0 hw) "Папка шаблонов SHEETS" 64)))
      (if (and f (not (vl-catch-all-error-p f)))
        (progn
          (setq it (vl-catch-all-apply 'vlax-get-property (list f 'Self)))
          (if (not (vl-catch-all-error-p it))
            (setq p (vl-catch-all-apply 'vlax-get-property (list it 'Path))))
          (if (and (= (type p) 'STR) (/= p "") (not (wcmatch p "::*")))
            (progn
              (setq sht:tdir (sht:dir-norm (vl-string-translate "/" "\\" p)))
              (setenv "SHT_TplDir" sht:tdir)
              (sht:tpl-fill)))
          (vl-catch-all-apply 'vlax-release-object (list f))))
      (vl-catch-all-apply 'vlax-release-object (list sh)))
    (set_tile "error" "Окно выбора папки недоступно.")))

;;; --------------------------------------------------------------------------
;;;  11. КОМАНДЫ
;;; --------------------------------------------------------------------------

;; Изменения общих полей: во все листы + в словарь чертежа (внутри одной «Отмены»)
(defun sht:commit-data (doc cur pend ens sdat / n sr)
  (vla-StartUndoMark doc)
  (setq n (sht:apply-common pend ens))
  (foreach p cur (setq sdat (sht:alist-put sdat (car p) (cdr p))))
  (sht:set-write sdat)
  (setq sr (sht:sign-auto T))                ; s0.7: фамилии поменялись — подписи
  (vla-EndUndoMark doc)
  (princ (strcat "\nДанные комплекта: изменено полей " (itoa (length pend))
                 (if (> n 0) (strcat ", записано в листов: " (itoa n)) ", листов в чертеже нет")
                 "."))
  (if sr (sht:sign-msg sr nil))
  n)

(defun c:SHEET_NEW ( / doc sdat ens attrs r ret pt rec en lr sr
                       sht:mode sht:fmt sht:mult sht:or sht:form sht:sc0 sht:no0 sht:title0 sht:res
                       sht:cur sht:diff sht:pend sht:gnl sht:nsh sht:obozn0 sht:sugg)
  (setq doc  (sht:doc)
        sdat (sht:prepare))
  (sht:dblclick-setup)
  (sht:defaults)
  (setq ens   (sht:sheets)
        attrs (mapcar 'sht:attrs ens)
        r     (sht:common-now attrs sdat)
        sht:cur    (car r)
        sht:diff   (cadr r)
        sht:gnl    (sht:gnums ens)
        sht:nsh    (length ens)
        sht:mode   'NEW
        sht:fmt    *sht_Fmt*
        sht:mult   *sht_Mult*
        sht:or     *sht_Orient*
        sht:form   *sht_Form*
        sht:sc0    *sht_Scale*
        ;; графа 1 форм 4, 5: прежнее обозначение (в этом сеансе), иначе шифр комплекта (s0.10)
        sht:obozn0 (cond ((and *sht_Obozn* (/= *sht_Obozn* "")) *sht_Obozn*) ((cdr (assoc "SHIFR" sht:cur))) (""))
        sht:no0    (sht:next-num (sht:gnums-of (sht:num-group sht:form sht:obozn0) sht:gnl))
        sht:sugg   sht:no0
        sht:title0 *sht_Title*
        ret        (sht:sheet-dialog))
  ;; «Данные комплекта» подтверждены — записать, даже если лист не вставляется
  (if sht:pend
    (setq sdat (progn (sht:commit-data doc sht:cur sht:pend ens sdat) (sht:set-read))))
  (if (= ret 1)
    (progn
      (setq *sht_Fmt*     (nth 0 sht:res)
            *sht_Mult*    (nth 1 sht:res)
            *sht_Orient*  (nth 2 sht:res)
            *sht_Form*    (nth 3 sht:res)
            *sht_Scale*   (nth 4 sht:res)
            *sht_SheetNo* (nth 5 sht:res)
            *sht_Title*   (nth 6 sht:res)
            *sht_Obozn*   (nth 7 sht:res))
      (sht:save-defaults)
      (setq rec (sht:fmt-rec *sht_Fmt* *sht_Mult*))
      (princ (strcat "\nЛист " (sht:fmt-label rec) (if (= *sht_Orient* "P") " вертикальный" " горизонтальный")
                     ", 1:" (sht:n2s *sht_Scale*) ", в модели "
                     (sht:n2s (* *sht_Scale* (car (sht:fmt-wh rec *sht_Orient*)))) " x "
                     (sht:n2s (* *sht_Scale* (cadr (sht:fmt-wh rec *sht_Orient*))))))
      (if (setq pt (getpoint "\nЛевый нижний угол листа (Enter - отмена): "))
        (progn
          (vla-StartUndoMark doc)
          (setq en (sht:insert rec *sht_Orient* *sht_Form* pt *sht_Scale*
                               (append sht:cur sht:pend
                                       (list (cons "SHEET" *sht_SheetNo*) (cons "TITLE" *sht_Title*)
                                             (cons "OBOZN" *sht_Obozn*)))))
          (sht:stage-layer (cdr (assoc "STAGE" sht:cur)))
          ;; данные комплекта запомнить в чертеже (первый лист — источник для следующих)
          (foreach p sht:cur (setq sdat (sht:alist-put sdat (car p) (cdr p))))
          (sht:set-write sdat)
          (setq sr (sht:sign-auto T))           ; подписи и логотип (s0.7)
          (setq lr (sht:list-auto T))           ; ведомость листов и «Листов» (s0.5)
          (vla-EndUndoMark doc)
          (princ (strcat "\nЛист " (if (= *sht_SheetNo* "") "(без номера)" *sht_SheetNo*)
                         " вставлен, блок " (sht:bname rec *sht_Orient* *sht_Form*)
                         ". Листов в чертеже: " (itoa (length (sht:sheets))) "."))
          (if lr (sht:list-msg lr nil))
          (if sr (sht:sign-msg sr nil)))
        (princ "\nЛист не вставлен."))))
  (sht:watch)
  (princ))

(defun c:SHEET_DATA () (sht:kit-cmd 'STAMP))

;; s0.11: данные бокового штампа — для всех листов
(defun c:SHEET_SIDE () (sht:kit-cmd 'SIDE))

;; s0.11: все поля штампа листа (выбранного до команды или щелчком)
(defun c:SHEET_STAMP ( / ss en)
  (sht:dblclick-setup)
  (if (and (setq ss (ssget "_I")) (sht:sheet-p (ssname ss 0)))
    (setq en (ssname ss 0)))
  (sssetfirst nil nil)
  (if (not en) (setq en (sht:pick "\nВыберите лист - рамку или штамп (Enter - выход): ")))
  (if en (sht:fw-edit en 'STAMP))
  (sht:watch)
  (princ))

;; Выбрать лист щелчком: промах — ещё раз, не лист — сообщение, Enter — nil
(defun sht:pick (msg / r e)
  (while (not r)
    (setq e (entsel msg))
    (cond
      (e (if (sht:sheet-p (car e))
           (setq r (car e))
           (princ "\nЭто не лист SHEETS - щёлкните рамку или штамп листа.")))
      ((= (getvar "ERRNO") 7) (princ "\nПромах."))
      (t (setq r 'EXIT))))
  (if (eq r 'EXIT) nil r))

;; Окно «Лист» для листа en: формат, кратность, ориентация, штамп, масштаб — замена блока на месте;
;; номер и наименование — в атрибуты; «Все поля штампа...» / «Данные бокового штампа...» — затем
;; окно-штамп этого листа (s0.11).
;; Возвращает ename листа (после замены — новый).
(defun sht:edit-sheet (en / doc sdat ens attrs r inf a0 ret rec changed new p lr sr
                          sht:mode sht:fmt sht:mult sht:or sht:form sht:sc0 sht:no0 sht:title0 sht:res
                          sht:cur sht:diff sht:pend sht:gnl sht:nsh sht:obozn0 sht:sugg)
  (setq doc   (sht:doc)
        sdat  (sht:prepare)
        ens   (sht:sheets)
        attrs (mapcar 'sht:attrs ens)
        r     (sht:common-now attrs sdat)
        inf   (sht:sheet-info en)
        a0    (sht:attrs en)
        sht:cur    (car r)
        sht:diff   (cadr r)
        sht:mode   'EDIT
        sht:fmt    (car (car inf))
        sht:mult   (cadr (car inf))
        sht:or     (cadr inf)
        sht:form   (caddr inf)
        sht:sc0    (cadddr inf)
        sht:no0    (sht:trim (cond ((cdr (assoc "SHEET" a0))) ("")))
        sht:title0 (cond ((cdr (assoc "TITLE" a0))) (""))
        sht:obozn0 (cond ((cdr (assoc "OBOZN" a0))) ((cdr (assoc "SHIFR" a0))) ((cdr (assoc "SHIFR" sht:cur))) (""))
        sht:gnl    (sht:gnums (vl-remove en ens))
        sht:nsh    (length ens)
        ret        (sht:sheet-dialog))
  (if sht:pend
    (setq sdat (progn (sht:commit-data doc sht:cur sht:pend ens sdat) (sht:set-read))))
  (if (member ret '(1 3 4))
    (progn
      (setq rec     (sht:fmt-rec (nth 0 sht:res) (nth 1 sht:res))
            changed (or (not (equal rec (car inf)))
                        (/= (nth 2 sht:res) (cadr inf))
                        (/= (nth 3 sht:res) (caddr inf))
                        (> (abs (- (nth 4 sht:res) (cadddr inf))) 1e-9))
            new     (list (cons "SHEET" (nth 5 sht:res)) (cons "TITLE" (nth 6 sht:res))
                          (cons "OBOZN" (nth 7 sht:res))))
      (vla-StartUndoMark doc)
      (if changed
        (setq en (sht:replace en rec (nth 2 sht:res) (nth 3 sht:res) (nth 4 sht:res) sht:cur new))
        (progn
          (foreach a (sht:att-objs en)
            (if (setq p (assoc (strcase (vla-get-TagString a)) new))
              (vla-put-TextString a (cdr p))))
          (sht:fit-sheet en)))
      (setq sr (sht:sign-auto T))               ; подписи и логотип (s0.7)
      (setq lr (sht:list-auto T))               ; ведомость листов и «Листов» (s0.5)
      (vla-EndUndoMark doc)
      (princ (strcat "\nЛист " (if (= (nth 5 sht:res) "") "(без номера)" (nth 5 sht:res))
                     (if changed
                       (strcat ": " (sht:fmt-label rec) (if (= (nth 2 sht:res) "P") " вертикальный" " горизонтальный")
                               ", 1:" (sht:n2s (nth 4 sht:res)) ", блок "
                               (sht:bname rec (nth 2 sht:res) (nth 3 sht:res)) " (заменён на том же месте).")
                       ": записано.")))
      (if lr (sht:list-msg lr nil))
      (if sr (sht:sign-msg sr nil))
      (cond                                     ; s0.11: окна в виде штампа для этого листа
        ((= ret 3) (sht:fw-edit en 'STAMP))
        ((= ret 4) (sht:fw-edit en 'SIDE)))))
  en)

(defun c:SHEET_EDIT ( / ss en)
  (sht:dblclick-setup)
  (if (and (setq ss (ssget "_I")) (sht:sheet-p (ssname ss 0)))
    (setq en (ssname ss 0)))
  (sssetfirst nil nil)
  (if (not en) (setq en (sht:pick "\nВыберите лист - рамку или штамп (Enter - выход): ")))
  (if en (sht:edit-sheet en))
  (sht:watch)
  (princ))

;; Двойной щелчок по листу — два пути (s0.2.2), срабатывает тот, что работает у AutoCAD пользователя:
;;  1) реактор мыши (раздел 12): щелчок по листу — гасит обычное действие (DBLCLKEDIT) и запускает
;;     SHEET_DBLEDIT; не зависит от настройки двойного щелчка в CUI;
;;  2) встроенная EATTEDIT отключается (UNDEFINE "_EATTEDIT" — английское имя: в русском AutoCAD
;;     "EATTEDIT" без "_" не находилась, s0.2.1), двойной щелчок по блоку с атрибутами вызывает c:EATTEDIT.
;; Окно открывается один раз: кто первый — открывает, второй видит это и молчит.
(defun c:EATTEDIT ( / ss en)
  (sht:dbl-restore)
  (setq ss (ssget "_I"))
  (if ss (setq en (ssname ss 0)))
  (sssetfirst nil nil)
  (cond
    ((and en (sht:sheet-p en))
     (setq *sht:DblEn* nil)                       ; SHEET_DBLEDIT от реактора — уже не нужна
     (sht:edit-sheet en)
     (sht:watch)
     (setq *sht:DblDone* (getvar "MILLISECS")))
    (en (command "_.EATTEDIT" en))
    ;; окно по этому двойному щелчку только что открыл реактор — не спрашивать блок
    ((and *sht:DblDone* (< (abs (- (getvar "MILLISECS") *sht:DblDone*)) 3000))
     (setq *sht:DblDone* nil))
    (t (command "_.EATTEDIT")))
  (princ))

;; Запускается реактором мыши: окно «Лист» для листа, по которому дважды щёлкнули
(defun c:SHEET_DBLEDIT ( / en)
  (sht:dbl-restore)
  (sht:dblclick-setup)                               ; s0.14: первый двойной щелчок — настройка здесь
  (setq en          *sht:DblEn*
        *sht:DblEn* nil)
  (cond
    ((not (and en (entget en) (sht:sheet-p en))))   ; окно уже открыл c:EATTEDIT
    ((= (getvar "BLOCKEDITOR") 1)
     (princ "\nSHEETS: двойной щелчок открыл редактор блоков - обычное действие не отключилось."))
    (t
     (sssetfirst nil nil)
     (sht:edit-sheet en)
     (sht:watch)
     (setq *sht:DblDone* (getvar "MILLISECS"))))
  (princ))

(defun sht:dblclick-setup ( / ce)
  (sht:react-ensure)
  (if (and (not *sht:DblOn*) (/= (getenv "SHT_DblClick") "0"))
    (progn
      (setq ce (getvar "CMDECHO"))
      (setvar "CMDECHO" 0)
      (command "_.UNDEFINE" "_EATTEDIT")
      (setvar "CMDECHO" ce)
      (setq *sht:DblOn* T)))
  *sht:DblOn*)

;; Включить / выключить окно «Лист» по двойному щелчку (запоминается в реестре)
(defun c:SHEET_DBLCLICK ( / ce)
  (setq ce (getvar "CMDECHO"))
  (setvar "CMDECHO" 0)
  (if (= (getenv "SHT_DblClick") "0")
    (progn
      (setenv "SHT_DblClick" "1")
      (sht:dblclick-setup)
      (princ "\nДвойной щелчок по листу: окно «Лист» (включено)."))
    (progn
      (setenv "SHT_DblClick" "0")
      (command "_.REDEFINE" "_EATTEDIT")
      (setq *sht:DblOn* nil)
      (if *sht:RMouse* (vlr-remove *sht:RMouse*))
      (setq *sht:RMouse* nil)
      (sht:dbl-restore)
      (princ "\nДвойной щелчок по листу: обычный редактор атрибутов (выключено).")))
  (setvar "CMDECHO" ce)
  (princ))

;; Вписать тексты всех листов в графы (после правки атрибутов в «Свойствах» или редакторе)
(defun c:SHEET_UPDATE ( / doc sdat r n lr sr)
  (setq doc  (sht:doc)
        sdat (sht:prepare))
  (sht:dblclick-setup)
  (vla-StartUndoMark doc)
  (sht:apply-props)
  (setq n (sht:fit-all)
        r (sht:common-now (mapcar 'sht:attrs (sht:sheets)) sdat))
  (sht:stage-layer (cdr (assoc "STAGE" (car r))))
  (setq lr (sht:list-update nil T))          ; ведомость листов и «Листов» (s0.5)
  (setq sr (sht:sign-sync T))                ; подписи и логотип — заново (s0.7)
  (vla-EndUndoMark doc)
  (sht:watch)
  (princ (strcat "\nЛистов обновлено: " (itoa n) " (тексты вписаны в графы)."))
  (sht:list-msg lr nil)
  (if sr (sht:sign-msg sr nil))
  (princ))

;; Разбор объекта (для перехода с СПДС): тип, класс, габарит, DXF-данные, свойства ActiveX
(defun c:SHEET_PROBE ( / e ed o on r mn mx)
  (if (setq e (car (entsel "\nОбъект для разбора (формат СПДС и т. п.): ")))
    (progn
      (setq ed (entget e)
            o  (vlax-ename->vla-object e)
            on (vl-catch-all-apply 'vla-get-ObjectName (list o)))
      (princ (strcat "\nТип: " (cdr (assoc 0 ed)) ", слой: " (cdr (assoc 8 ed))
                     (if (= (type on) 'STR) (strcat ", класс: " on) "")))
      (setq r (vl-catch-all-apply 'vla-GetBoundingBox (list o 'mn 'mx)))
      (if (not (vl-catch-all-error-p r))
        (progn
          (setq mn (vlax-safearray->list mn)
                mx (vlax-safearray->list mx))
          (princ (strcat "\nГабарит: " (sht:n2s (- (car mx) (car mn))) " x " (sht:n2s (- (cadr mx) (cadr mn)))
                         ", левый нижний угол " (sht:n2s (car mn)) "," (sht:n2s (cadr mn))))))
      (princ "\n--- DXF (без двоичных данных):")
      (foreach g ed
        (if (not (member (car g) '(310 -1 330 360)))
          (progn (princ "\n") (prin1 g))))
      (princ "\n--- свойства ActiveX:")
      (vl-catch-all-apply 'vlax-dump-object (list o T))
      (textscr)))
  (princ))

;;; --------------------------------------------------------------------------
;;;  12. ФОРМАТ В «СВОЙСТВАХ» И РЕАКТОРЫ (s0.2.2)
;;; --------------------------------------------------------------------------
;; Лист: атрибут FORMAT (графа 26: «A3», «A4x3») и невидимый ORIENT («горизонтальная» / «вертикальная»)
;; видны в «Свойствах» (раздел «Атрибуты»). Поменяли — реактор на этих атрибутах запускает SHEET_APPLY:
;; лист перестраивается на месте (как из окна «Лист»). Выпадающий список в «Свойствах» бывает только
;; у динамических блоков — из LISP их не создать, поэтому значение вписывается.

;; Формат из записи: "A3", "a4x3", «А4х3» (кириллица), "A0 x 2" -> запись формата или nil
(defun sht:parse-fmt (s / i)
  (setq s (strcase (vl-string-translate "АаХх*" "AaXxx" (sht:trim s))))
  (while (setq i (vl-string-search " " s))
    (setq s (strcat (substr s 1 i) (substr s (+ i 2)))))
  (cond
    ((not (wcmatch s "A#,A#X#")) nil)
    ((setq i (vl-string-search "X" s)) (sht:fmt-rec (substr s 1 i) (atoi (substr s (+ i 2)))))
    (t (sht:fmt-rec s 1))))

;; Ориентация из записи: г / горизонтальная / L -> "L"; в / вертикальная / P -> "P"; иначе nil
(defun sht:parse-orient (s / c)
  (setq c (substr (sht:trim s) 1 1))
  (cond ((member c '("г" "Г" "L" "l" "H" "h")) "L")
        ((member c '("в" "В" "P" "p" "V" "v")) "P")))

;; Формат / ориентация в атрибутах листа против блока: nil — совпадают; (запись ориентация) — поменяли;
;; BAD — запись не понята
(defun sht:props-want (en / inf a f o rec orient)
  (setq inf (sht:sheet-info en)
        a   (sht:attrs en)
        f   (cdr (assoc "FORMAT" a))
        o   (cdr (assoc "ORIENT" a)))
  (if (and inf f o)
    (progn
      (setq rec    (sht:parse-fmt f)
            orient (sht:parse-orient o))
      (if (and rec (sht:portrait-only-p (car rec) (cadr rec))) (setq orient "P"))
      (cond
        ((or (null rec) (null orient)) 'BAD)
        ((and (equal rec (car inf)) (= orient (cadr inf))) nil)
        (t (list rec orient))))))

;; Записать в FORMAT / ORIENT формат и ориентацию блока (вид «A3», «вертикальная»)
(defun sht:props-reset (en inf / tag v)
  (foreach a (sht:att-objs en)
    (setq tag (strcase (vla-get-TagString a))
          v   (cond ((= tag "FORMAT") (sht:fmt-label (car inf)))
                    ((= tag "ORIENT") (sht:orient-name (cadr inf)))))
    (if (and v (/= v (vla-get-TextString a)))
      (vla-put-TextString a v))))

(defun sht:sheet-no (en / s)
  (setq s (sht:trim (cdr (assoc "SHEET" (sht:attrs en)))))
  (if (= s "") "(без номера)" s))

(defun sht:fmt-list-str ( / res)
  (foreach r *sht:Formats* (setq res (cons (sht:fmt-label r) res)))
  (setq res (reverse res))
  (apply 'strcat (cons (car res) (mapcar '(lambda (x) (strcat ", " x)) (cdr res)))))

;; Перестроить листы, у которых FORMAT / ORIENT не совпадают с блоком; непонятная запись —
;; вернуть прежнюю. Возвращает (набор-новых-листов-или-nil число).
(defun sht:apply-props ( / inf a w new sel n)
  (setq sel (ssadd)
        n   0)
  (foreach en (sht:sheets)
    (setq inf (sht:sheet-info en)
          a   (sht:attrs en)
          w   (sht:props-want en))
    (cond
      ((eq w 'BAD)
       (princ (strcat "\nЛист " (sht:sheet-no en) ": не понято «" (cond ((cdr (assoc "FORMAT" a))) (""))
                      "» / «" (cond ((cdr (assoc "ORIENT" a))) ("")) "» - оставлен " (sht:fmt-label (car inf))
                      ", " (sht:orient-name (cadr inf)) ".\n  Форматы: " (sht:fmt-list-str)
                      ".\n  Ориентация: горизонтальная / вертикальная (можно г / в)."))
       (sht:props-reset en inf))
      (w
       (setq new (sht:replace en (car w) (cadr w) (caddr inf) (cadddr inf) nil nil)
             n   (1+ n))
       (ssadd new sel)
       (princ (strcat "\nЛист " (sht:sheet-no new) ": " (sht:fmt-label (car w)) ", " (sht:orient-name (cadr w))
                      " - перестроен на месте, блок " (sht:bname (car w) (cadr w) (caddr inf)) ".")))
      (t (sht:props-reset en inf))))
  (list (if (> n 0) sel) n))

;; Формат / ориентация поменяли в «Свойствах» (или в редакторе атрибутов) — перестроить листы.
;; Запускается сама (реактор), можно и вручную.
(defun c:SHEET_APPLY ( / doc r)
  (setq *sht:ApplyQ* nil
        doc          (sht:doc))
  (sht:prepare)
  (vla-StartUndoMark doc)
  (setq r (sht:apply-props))
  (sht:sign-auto nil)                        ; s0.7
  (vla-EndUndoMark doc)
  (sht:watch)
  (if (car r) (sssetfirst nil (car r)))      ; новые листы — выделены, «Свойства» показывают их
  (princ))

;; --- реакторы: метка "SHEETS" (при повторной загрузке файла прежние снимаются) ---
(defun sht:react-remove ()
  (foreach grp (vlr-reactors :vlr-mouse-reactor :vlr-editor-reactor :vlr-object-reactor)
    (foreach r (cdr grp)
      (if (= (vlr-data r) "SHEETS") (vlr-remove r))))
  (setq *sht:RMouse* nil *sht:REditor* nil *sht:RAtts* nil *sht:RTbls* nil *sht:TblDirty* nil
        *sht:RSign* nil *sht:SignDirty* nil))

(defun sht:react-ensure ()
  (if (not *sht:REditor*)
    (setq *sht:REditor*
      (vlr-editor-reactor "SHEETS"
        '((:vlr-commandWillStart . sht:r-cmd-start) (:vlr-commandEnded . sht:r-cmd-end)
          (:vlr-commandCancelled . sht:r-cmd-end) (:vlr-commandFailed . sht:r-cmd-end)))))
  (if (and (/= (getenv "SHT_DblClick") "0") (not *sht:RMouse*))
    (setq *sht:RMouse* (vlr-mouse-reactor "SHEETS" '((:vlr-beginDoubleClick . sht:r-dbl)))))
  (if (not *sht:RAtts*) (sht:watch))
  (if (not *sht:RTbls*) (sht:tbl-watch))          ; s0.6.1: таблицы (спецификации)
  T)

;; Число вставок SHT_* в чертеже (изменилось — пересобрать наблюдение)
(defun sht:sheet-count ( / ss)
  (if (setq ss (ssget "_X" '((0 . "INSERT") (2 . "SHT_*")))) (sslength ss) 0))

;; Число таблиц AutoCAD в чертеже (s0.6: изменилось и есть ведомость спецификаций — обновить её)
(defun sht:table-count ( / ss)
  (if (setq ss (ssget "_X" '((0 . "ACAD_TABLE")))) (sslength ss) 0))

;; s0.6.1: наблюдать за всеми таблицами, кроме таблиц SHEETS: изменилась (правка ячейки, перенос, ручки,
;; «Свойства») — флаг *sht:TblDirty*; в конце команды есть флаг и ведомость спецификаций — обновить её
;; (sht:watch-check). Сам реактор ничего в чертеже не меняет. Возвращает число таблиц под наблюдением.
(defun sht:tbl-watch ( / ss i en objs)
  (if *sht:RTbls* (vlr-remove *sht:RTbls*))
  (setq *sht:RTbls*    nil
        *sht:TblDirty* nil)
  (if (setq ss (ssget "_X" '((0 . "ACAD_TABLE"))))
    (progn
      (setq i 0)
      (while (< i (sslength ss))
        (setq en (ssname ss i)
              i  (1+ i))
        (if (not (sht:tbl-mark en))
          (setq objs (cons (vlax-ename->vla-object en) objs))))))
  (if objs
    (setq *sht:RTbls* (vlr-object-reactor objs "SHEETS" '((:vlr-modified . sht:r-tbl-mod)))))
  (length objs))

(defun sht:r-tbl-mod (obj r args)
  (setq *sht:TblDirty* T)
  (princ))

;; Наблюдать за атрибутами FORMAT / ORIENT всех листов; запомнить их значения
(defun sht:watch ( / objs tag)
  (if *sht:RAtts* (vlr-remove *sht:RAtts*))
  (setq *sht:RAtts*     nil
        *sht:WatchVals* nil)
  (foreach en (sht:sheets)
    (foreach a (sht:att-objs en)
      (setq tag (strcase (vla-get-TagString a)))
      (if (member tag '("FORMAT" "ORIENT"))
        (setq objs            (cons a objs)
              *sht:WatchVals* (cons (cons (vla-get-Handle a) (vla-get-TextString a)) *sht:WatchVals*)))))
  (if objs
    (setq *sht:RAtts* (vlr-object-reactor objs "SHEETS" '((:vlr-modified . sht:r-att-mod)))))
  (sht:sign-watch)                               ; s0.7: листы и фамилии — для подписей
  (setq *sht:SignDirty* nil
        *sht:WatchCnt* (sht:sheet-count)
        *sht:WatchTbl* (sht:table-count))
  (length objs))

;; Атрибут FORMAT / ORIENT изменён: значение другое — поставить SHEET_APPLY в очередь (один раз)
(defun sht:r-att-mod (obj r args)
  (vl-catch-all-apply 'sht:on-att-mod (list obj))
  (princ))

(defun sht:on-att-mod (obj / old)
  (if (and (not *sht:ApplyQ*)
           (not (vlax-erased-p obj))
           (setq old (assoc (vla-get-Handle obj) *sht:WatchVals*))
           (/= (cdr old) (vla-get-TextString obj)))
    (progn
      (setq *sht:ApplyQ* T)
      (if (vl-catch-all-error-p (vl-catch-all-apply 'vla-SendCommand (list (sht:doc) "_SHEET_APPLY ")))
        (progn
          (setq *sht:ApplyQ* nil)
          (princ "\nSHEETS: формат / ориентация листа изменены - чтобы перестроить лист, введите SHEET_APPLY."))))))

;; Начало любой команды — вернуть двойной щелчок (DBLCLKEDIT), если гасили;
;; s0.5: перед сохранением и печатью — обновить ведомость листов и «Листов»; s0.7: сначала подписи и логотип
(defun sht:r-cmd-start (r args)
  (vl-catch-all-apply 'sht:dbl-restore nil)
  (if (and (= (type (car args)) 'STR) (member (strcase (car args)) *sht:ListCmds*))
    (progn
      (vl-catch-all-apply 'sht:sign-auto (list nil))
      (vl-catch-all-apply 'sht:list-auto (list nil))))
  (princ))

;; Конец команды: копирование, отмена и т. п. — пересобрать наблюдение за атрибутами;
;; s0.5.1: листов стало больше / меньше — сразу ведомость листов (sht:watch-check)
(defun sht:r-cmd-end (r args)
  (setq *sht:ApplyQ* nil)
  (vl-catch-all-apply 'sht:watch-check (list (car args)))
  (princ))

(defun sht:watch-check (cmd / chg tc chgt dirty undo sdirty)
  (setq cmd   (if (= (type cmd) 'STR) (strcase cmd) "")
        undo  (wcmatch cmd "U,UNDO,REDO,MREDO")
        chg   (/= (sht:sheet-count) *sht:WatchCnt*)
        tc    (sht:table-count)
        chgt  (/= tc *sht:WatchTbl*)
        dirty *sht:TblDirty*
        sdirty *sht:SignDirty*            ; s0.7: лист сдвинули, фамилию поменяли
        *sht:SignDirty* nil)
  (if (or chg (wcmatch cmd "U,UNDO,REDO,MREDO,OOPS,ATTSYNC,BATTMAN"))
    (sht:watch))
  ;; s0.6.1: таблиц стало больше / меньше, отмена — наблюдение за таблицами заново (флаг снимается)
  (if (or chgt undo (= cmd "OOPS"))
    (sht:tbl-watch))
  (setq *sht:WatchTbl* tc
        *sht:TblDirty* nil)
  ;; s0.5.1: число листов изменилось (ERASE, Delete, вырезать, копировать, вставить …) — ведомость сразу.
  ;; s0.6: число таблиц изменилось (спецификацию вставили, удалили) и есть ведомость спецификаций — тоже;
  ;; s0.6.1: и когда таблица изменилась (заголовок поправили — TABLEDIT, перенесли — MOVE, ручки …).
  ;; После U / UNDO / REDO — нет: своя запись «Отмены» перепутала бы цепочку; обновится при сохранении.
  ;; s0.7: подписи и логотип — листов стало больше / меньше, лист сдвинули, фамилию поменяли (так же, не после U)
  (if (and (or chg sdirty) (not undo))
    (sht:sign-auto nil))
  (if (and (or chg (and (or chgt dirty) (sht:kind-tables "SPEC")))
           (not undo))
    (sht:list-auto nil))
  ;; s0.13: ведомость перенесли на другое место / лист — разрыв по высоте листа
  (if (not undo) (sht:brk-all)))

;; --- двойной щелчок (реактор мыши) ---
(defun sht:dbl-on-p ( / v)
  (setq v (getvar "DBLCLKEDIT"))
  (or (equal v 1) (and (= (type v) 'STR) (= (strcase v) "ON"))))

(defun sht:dbl-set (on / v)
  (setq v (getvar "DBLCLKEDIT"))
  (vl-catch-all-apply 'setvar (list "DBLCLKEDIT" (if (= (type v) 'STR) (if on "ON" "OFF") (if on 1 0)))))

;; Двойной щелчок гасили — включить (метка в реестре: и после сбоя AutoCAD)
(defun sht:dbl-restore ()
  (if (= (getenv "SHT_DblOff") "1")
    (progn
      (setenv "SHT_DblOff" "0")
      (sht:dbl-set T))))

;; Лист под точкой двойного щелчка (рамка, штамп или атрибут) или nil
(defun sht:dbl-target (pt / r e ed ss)
  (setq r (vl-catch-all-apply 'nentselp (list (trans pt 0 1))))
  (cond
    ((vl-catch-all-error-p r)                ; nentselp недоступен — лист, выделенный первым щелчком
     (if (and (setq ss (cadr (ssgetfirst))) (= (sslength ss) 1))
       (setq e (ssname ss 0))))
    ((and r (setq ed (entget (car r))))
     (cond
       ((= (cdr (assoc 0 ed)) "ATTRIB") (setq e (cdr (assoc 330 ed))))
       ((and (cadddr r) (listp (cadddr r))) (setq e (last (cadddr r)))))))
  (if (and e (sht:sheet-p e)) e))

(defun sht:r-dbl (r args)
  (vl-catch-all-apply 'sht:on-dbl (list (car args)))
  (princ))

(defun sht:on-dbl (pt / en)
  (sht:dbl-restore)
  (setq *sht:DblDone* nil)
  (if (and (= (getvar "CMDNAMES") "")
           (sht:dbl-on-p)
           (setq en (sht:dbl-target pt)))
    (progn
      (setq *sht:DblEn* en)
      (setenv "SHT_DblOff" "1")
      (sht:dbl-set nil)                      ; обычное действие двойного щелчка — на этот раз нет
      (if (vl-catch-all-error-p (vl-catch-all-apply 'vla-SendCommand (list (sht:doc) "_SHEET_DBLEDIT ")))
        (progn
          (sht:dbl-restore)
          (setq *sht:DblEn* nil)
          (princ "\nSHEETS: окно листа по двойному щелчку не открылось - используйте SHEET_EDIT."))))))

;;; --------------------------------------------------------------------------
;;;  13. ПЕЧАТЬ В PDF (s0.3): SHEET_PLOT
;;;  Листы — по номерам (sht:num<); без номера не печатаются (список — в командной строке и в окне).
;;;  На каждый лист — временный набор параметров листа модели SHT_PLOT_<время>_nnn: DWG To PDF.pc3,
;;;  бумага — по размеру листа (кандидаты — по двум последним числам канонического имени,
;;;  размер и поля — у плоттера: GetPaperSize / GetPaperMargins; лучше без полей, затем без поворота),
;;;  окно = лист в модели (в экранных координатах: trans 0 -> 2), масштаб 1:масштаб листа, по центру.
;;;  Один PDF — -PUBLISH по списку DSD (Type=6, закладки «Лист N. Наименование»);
;;;  отдельные файлы — PlotToFile с параметрами листа модели (прежние — в SHT_PLOTSAVE, возвращаются).
;;;  Временные наборы удаляются после печати, при ошибке и при следующем запуске (после сбоя).
;;; --------------------------------------------------------------------------

(setq *sht:Pc3*       "DWG To PDF.pc3"
      *sht:PcPrefix*  "SHT_PLOT_"        ; временные наборы параметров листа
      *sht:PcSave*    "SHT_PLOTSAVE"     ; копия параметров листа модели на время печати
      *sht:PlotSaved* nil                ; системные переменные до печати: ((имя . значение) …)
      *sht:ModelArea* nil)               ; область печати листа модели до печати (s0.3.2)

(defun sht:pcs () (vla-get-PlotConfigurations (sht:doc)))
(defun sht:model-layout () (vla-get-Layout (sht:ms)))

;; Набор параметров листа по имени или nil
(defun sht:pc-get (name / r)
  (setq r (vl-catch-all-apply 'vla-Item (list (sht:pcs) name)))
  (if (vl-catch-all-error-p r) nil r))

;; Удалить временные наборы SHT_PLOT_*; осталась копия параметров модели (сбой печати) — вернуть её.
;; Возвращает число удалённых наборов.
(defun sht:pc-purge ( / lst sv pc)
  (vlax-for pc (sht:pcs)
    (if (wcmatch (strcase (vla-get-Name pc)) (strcat *sht:PcPrefix* "*"))
      (setq lst (cons pc lst))))
  (foreach pc lst (vl-catch-all-apply 'vla-Delete (list pc)))
  (if (setq sv (sht:pc-get *sht:PcSave*))
    (progn
      (vl-catch-all-apply 'vla-CopyFrom (list (sht:model-layout) sv))
      (if *sht:ModelArea* (sht:model-area-set (sht:model-layout) *sht:ModelArea*))
      (vl-catch-all-apply 'vla-Delete (list sv))))
  (setq *sht:ModelArea* nil)
  (length lst))

;; Системные переменные на время печати: lst — ((имя . значение) …); прежние — в *sht:PlotSaved*
(defun sht:plot-sv-set (lst / v)
  (foreach p lst
    (setq v (getvar (car p)))
    (if (and v (not (assoc (car p) *sht:PlotSaved*)))
      (setq *sht:PlotSaved* (cons (cons (car p) v) *sht:PlotSaved*)))
    (if (and v (not (equal v (cdr p))))
      (vl-catch-all-apply 'setvar (list (car p) (cdr p))))))

;; После печати и при ошибке: временные наборы, параметры модели, системные переменные
(defun sht:plot-cleanup ()
  (vl-catch-all-apply 'sht:pc-purge nil)
  (foreach p *sht:PlotSaved*
    (if (not (equal (getvar (car p)) (cdr p)))
      (vl-catch-all-apply 'setvar (list (car p) (cdr p)))))
  (setq *sht:PlotSaved* nil))

;; --- строки, имена файлов, папки -------------------------------------------

;; Текст атрибута без кодов многострочного текста: «\P» — пробел, фигурные скобки убрать
(defun sht:plain (s / i)
  (setq s (if s s ""))
  (while (setq i (vl-string-search "\\P" s))
    (setq s (strcat (substr s 1 i) " " (substr s (+ i 3)))))
  (sht:trim (vl-string-translate "{}" "  " s)))

;; Склеить строки через sep
(defun sht:join (lst sep / s)
  (setq s nil)
  (foreach x lst (setq s (if s (strcat s sep x) x)))
  (if s s ""))

;; Имя файла: недопустимые знаки \ / : * ? " < > | и табуляция — на «_»; без точек и пробелов в конце
(defun sht:fname (s)
  (vl-string-right-trim ". " (sht:trim (vl-string-translate "\\/:*?\"<>|\t" "__________" s))))

;; Сделать имя уникальным среди used (без учёта регистра): «имя», «имя (2)», …
(defun sht:uniq-name (s used / n r up)
  (setq up (mapcar 'strcase used)
        r  s
        n  1)
  (while (member (strcase r) up)
    (setq n (1+ n)
          r (strcat s " (" (itoa n) ")")))
  r)

(defun sht:pad3 (k / s)
  (setq s (itoa k))
  (while (< (strlen s) 3) (setq s (strcat "0" s)))
  s)

;; Целые без повторов, по возрастанию; (sht:range 0 3) -> (0 1 2)
(defun sht:uniq-sort (lst / res)
  (foreach x lst (if (not (member x res)) (setq res (cons x res))))
  (vl-sort res '<))

(defun sht:range (a b / res)
  (while (< a b)
    (setq b   (1- b)
          res (cons b res)))
  res)

;; Индексы списка окна: "0 3 5" <-> (0 3 5)
(defun sht:idx-read (s / res)
  (foreach x (sht:split (sht:trim s) " ")
    (if (/= x "") (setq res (cons (atoi x) res))))
  (reverse res))

(defun sht:idx-str (lst)
  (sht:join (mapcar 'itoa lst) " "))

(defun sht:find-ci (s lst)
  (vl-some '(lambda (x) (if (= (strcase x) (strcase s)) x)) lst))

(defun sht:dir-norm (d) (vl-string-right-trim "\\/ " (sht:trim d)))
(defun sht:plot-dir-default () (strcat (getvar "DWGPREFIX") "PDF"))

;; Папка для PDF: выбранная для этого чертежа (словарь SHT_SET, ключ @PDFDIR) или подпапка PDF у чертежа
(defun sht:plot-dir-load (sdat / d)
  (setq d (sht:dir-norm (cdr (assoc "@PDFDIR" sdat))))
  (if (= d "") (sht:plot-dir-default) d))

(defun sht:plot-dir-save (dir / sdat old new)
  (setq sdat (sht:set-read)
        old  (cond ((cdr (assoc "@PDFDIR" sdat))) (""))
        new  (if (= (strcase dir) (strcase (sht:plot-dir-default))) "" dir))
  (if (/= old new) (sht:set-write (sht:alist-put sdat "@PDFDIR" new))))

;; Создать папку (и недостающие выше). T — папка есть
(defun sht:mkdir (d / up)
  (cond
    ((vl-file-directory-p d) T)
    ((and (setq up (vl-filename-directory d)) (/= up "") (/= (strcase up) (strcase d)) (sht:mkdir up))
     (vl-mkdir d)
     (vl-file-directory-p d))))

;; Открыть файл или папку в Windows (программа просмотра PDF / Проводник)
(defun sht:open-path (p / sh r)
  (setq sh (vl-catch-all-apply 'vlax-create-object (list "Shell.Application")))
  (if (and sh (not (vl-catch-all-error-p sh)))
    (progn
      (setq r (vl-catch-all-apply 'vlax-invoke (list sh 'ShellExecute p)))
      (vl-catch-all-apply 'vlax-release-object (list sh)))
    (setq r (vl-catch-all-error-p T)))
  (if (or (null sh) (vl-catch-all-error-p sh) (vl-catch-all-error-p r))
    (vl-catch-all-apply 'startapp (list "explorer.exe" (strcat "\"" p "\"")))))

;; --- листы для печати ---------------------------------------------------------

;; Лист: (ename номер наименование формат ориентация масштаб точка ширина высота поворот шифр)
(defun sht:plot-item (en / inf a wh ed)
  (setq inf (sht:sheet-info en)
        a   (sht:attrs en)
        wh  (sht:fmt-wh (car inf) (cadr inf))
        ed  (entget en))
  ;; 10 — графа 1 (шифр; у форм 4, 5 — обозначение документа), 11 — 0 основной комплект (форма 3) /
  ;; 1 документы форм 4, 5, 6 (s0.10), 12 — форма
  (list en (sht:trim (cdr (assoc "SHEET" a))) (sht:plain (cdr (assoc "TITLE" a)))
        (sht:fmt-label (car inf)) (cadr inf) (cadddr inf) (nth 4 inf) (car wh) (cadr wh)
        (cond ((cdr (assoc 50 ed))) (0.0))
        (sht:plain (cdr (assoc (if (sht:fdoc-p (caddr inf)) "OBOZN" "SHIFR") a)))
        (if (= (sht:fbase (caddr inf)) "3") 0 1)
        (caddr inf)))

;; Естественный порядок строк (s0.10): цифры подряд — числом («КЖИ2» < «КЖИ10»), прочее — по знакам
;; без учёта регистра
(defun sht:nat-key (s / i n c d res)
  (setq s (sht:lc (sht:trim (if (= (type s) 'STR) s "")))
        i 1
        n (strlen s))
  (while (<= i n)
    (setq c (substr s i 1))
    (if (wcmatch c "#")
      (progn
        (setq d 0.0)
        (while (and (<= i n) (wcmatch (setq c (substr s i 1)) "#"))
          (setq d (+ (* d 10.0) (atoi c))
                i (1+ i)))
        (setq res (cons (list 0 d) res)))
      (setq res (cons (list 1 (ascii c)) res)
            i   (1+ i))))
  (apply 'append (reverse res)))

(defun sht:nat< (a b) (sht:key< (sht:nat-key a) (sht:nat-key b)))

;; Порядок печати (s0.10, решение Артёма): сначала основной комплект (форма 3) по номерам, затем
;; документы форм 4, 5, 6 по обозначению (графа 1), внутри — по номерам
(defun sht:plot< (a b)
  (cond
    ((< (nth 11 a) (nth 11 b)) T)
    ((> (nth 11 a) (nth 11 b)) nil)
    ((= (nth 11 a) 0) (sht:item< a b))
    ((sht:nat< (nth 10 a) (nth 10 b)) T)
    ((sht:nat< (nth 10 b) (nth 10 a)) nil)
    (t (sht:item< a b))))

;; Лист для сообщений: «Лист 3»; у документов форм 4-6 — «‹обозначение›, лист 2» / «‹обозначение›»
(defun sht:plot-sheet (it)
  (cond ((/= (nth 11 it) 1) (strcat "Лист " (nth 1 it)))
        ((= (nth 1 it) "") (nth 10 it))
        (t (strcat (nth 10 it) ", лист " (nth 1 it)))))

;; Порядок: по номеру; одинаковые номера — слева направо, затем сверху вниз
(defun sht:item< (a b)
  (cond
    ((sht:num< (nth 1 a) (nth 1 b)) T)
    ((sht:num< (nth 1 b) (nth 1 a)) nil)
    ((< (car (nth 6 a)) (car (nth 6 b))) T)
    ((> (car (nth 6 a)) (car (nth 6 b))) nil)
    (t (> (cadr (nth 6 a)) (cadr (nth 6 b))))))

;; Листы модели: (печатаемые-по-порядку без-номера). s0.10: лист документа формы 4 / 5 без номера
;; (однолистовой документ) — печатается
(defun sht:plot-items ( / it on off)
  (foreach en (sht:sheets)
    (setq it (sht:plot-item en))
    (if (and (= (nth 1 it) "") (not (sht:fdoc-p (nth 12 it))))
      (setq off (cons it off))
      (setq on (cons it on))))
  (list (vl-sort on 'sht:plot<) (reverse off)))

(defun sht:plot-fmt (it)
  (strcat (nth 3 it) (if (= (nth 4 it) "P") " верт." " гор.") " 1:" (sht:n2s (nth 5 it))))

;; Строка списка окна: номер, формат, масштаб, наименование (через табуляцию)
(defun sht:plot-line (it)
  (strcat (if (= (nth 1 it) "") "-" (nth 1 it)) "\t" (nth 3 it) (if (= (nth 4 it) "P") " верт." " гор.")
          "\t1:" (sht:n2s (nth 5 it)) "\t"
          (if (= (nth 11 it) 1) (strcat (nth 10 it) (if (/= (nth 2 it) "") ". " "")) "")
          (nth 2 it)))

;; Описание листа для сообщений
(defun sht:plot-desc (it)
  (strcat (sht:plot-fmt it) (if (/= (nth 2 it) "") (strcat " «" (nth 2 it) "»") "")
          ", угол " (sht:n2s (car (nth 6 it))) "," (sht:n2s (cadr (nth 6 it)))))

;; Повторяющиеся номера (sht:pitems); у документов форм 4-6 — внутри документа (s0.10)
(defun sht:plot-dups ( / seen res k nm)
  (foreach it sht:pitems
    (if (/= (nth 1 it) "")
      (progn
        (setq k  (strcat (if (= (nth 11 it) 1) (strcat (sht:lc (nth 10 it)) "|") "") (strcase (nth 1 it)))
              nm (if (= (nth 11 it) 1) (sht:plot-sheet it) (nth 1 it)))
        (if (member k seen)
          (if (not (member nm res)) (setq res (cons nm res)))
          (setq seen (cons k seen))))))
  (reverse res))

;; Листы без номера и повторы номеров — в командную строку
(defun sht:plot-warn-off ( / d)
  (if sht:poff
    (progn
      (princ (strcat "\nЛисты без номера - не печатаются (" (itoa (length sht:poff)) "):"))
      (foreach it sht:poff (princ (strcat "\n  " (sht:plot-desc it))))))
  (if (setq d (sht:plot-dups))
    (princ (strcat "\nВНИМАНИЕ: номера листов повторяются: " (sht:join d ", ") "."))))

;; Строка окна о листах без номера и повторах
(defun sht:plot-off-str ( / s d)
  (setq s "")
  (if sht:poff
    (setq s (strcat "Без номера - не печатаются (" (itoa (length sht:poff)) "): "
                    (sht:join (mapcar 'sht:plot-desc sht:poff) "; "))))
  (if (setq d (sht:plot-dups))
    (setq s (strcat (if (= s "") "" (strcat s ". ")) "Повторяются номера: " (sht:join d ", "))))
  (if (> (strlen s) 100) (strcat (substr s 1 97) "...") s))

;; Выбранные до команды объекты (ename); выделение снять
(defun sht:plot-presel0 ( / ss i res)
  (if (setq ss (ssget "_I"))
    (progn
      (setq i 0)
      (while (< i (sslength ss))
        (setq res (cons (ssname ss i) res)
              i   (1+ i)))))
  (sssetfirst nil nil)
  res)

;; Отметка в окне при открытии: выбранные до команды листы, иначе все
(defun sht:plot-presel (ens / k res)
  (setq k 0)
  (foreach it sht:pitems
    (if (member (car it) ens) (setq res (cons k res)))
    (setq k (1+ k)))
  (if res (reverse res) (sht:range 0 (length sht:pitems))))

(defun sht:pick-items (idx)
  (vl-remove nil (mapcar '(lambda (i) (nth i sht:pitems)) idx)))

;; Отметка по номерам: «1-5, 7, 1.1»; диапазон — по порядку номеров («-5» — от начала, «7-» — до конца).
;; s0.10: только листы основного комплекта (документы форм 4-6 — щелчком в списке).
;; Возвращает (индексы-в-items ненайденное)
(defun sht:nums-pick (s items / res miss part i a b k ok)
  (foreach p0 (sht:split (vl-string-translate ";" "," s) ",")
    (setq part (sht:trim p0))
    (cond
      ((= part ""))
      ((setq i (vl-string-search "-" part))
       (setq a  (sht:trim (substr part 1 i))
             b  (sht:trim (substr part (+ i 2)))
             k  0
             ok nil)
       (foreach it items
         (if (and (/= (nth 11 it) 1)
                  (or (= a "") (not (sht:num< (nth 1 it) a)))
                  (or (= b "") (not (sht:num< b (nth 1 it)))))
           (setq res (cons k res)
                 ok  T))
         (setq k (1+ k)))
       (if (not ok) (setq miss (cons part miss))))
      (t
       (foreach tok (sht:split part " ")
         (if (/= tok "")
           (progn
             (setq k 0 ok nil)
             (foreach it items
               (if (and (/= (nth 11 it) 1) (= (strcase (nth 1 it)) (strcase tok)))
                 (setq res (cons k res)
                       ok  T))
               (setq k (1+ k)))
             (if (not ok) (setq miss (cons tok miss)))))))))
  (list (sht:uniq-sort res) (reverse miss)))

;; Шифр для имени файла: самый частый непустой на листах основного комплекта (s0.10), нет — на любых;
;; нет и там — имя чертежа без расширения
(defun sht:plot-shifr (items / v w)
  (foreach it items
    (if (/= (nth 10 it) "")
      (if (/= (nth 11 it) 1) (setq v (cons (nth 10 it) v)) (setq w (cons (nth 10 it) w)))))
  (cond (v (sht:most (reverse v)))
        (w (sht:most (reverse w)))
        (t (vl-filename-base (getvar "DWGNAME")))))

;; Файл комплекта: «<шифр>.pdf»; файл листа (без расширения): «<шифр>_Лист <N>»
(defun sht:plot-file-all (items / s)
  (setq s (sht:fname (sht:plot-shifr items)))
  (strcat (if (= s "") "Комплект" s) ".pdf"))

;; s0.10: документ формы 4 / 5 — «‹обозначение›_Лист N», без номера — «‹обозначение›»
(defun sht:plot-file-base (it base)
  (sht:fname (strcat (if (/= (nth 10 it) "") (nth 10 it) base)
                     (if (= (nth 1 it) "") "" (strcat "_Лист " (nth 1 it))))))

(defun sht:plot-file-one (it base) (strcat (sht:plot-file-base it base) ".pdf"))

;; Имя листа в PDF (закладка): «Лист 3. Наименование». Знаки, которых AutoCAD может не принять
;; в имени листа (и скобки разделов списка): [ ] \ / : * ? " < > | = -> ( ) - - . x пробел ' ( ) - -
(defun sht:dsd-name (it / s)
  (setq s (vl-string-translate "[]\\/:*?\"<>|=" "()--.x '()--"
                               (strcat (sht:plot-sheet it) (if (/= (nth 2 it) "") (strcat ". " (nth 2 it)) ""))))
  (if (> (strlen s) 120) (strcat (substr s 1 117) "...") s))

;; --- плоттер, бумага, наборы параметров ---------------------------------------

;; Стили печати: CTB (чертёж в цветозависимом режиме, PSTYLEMODE = 1) или STB (именованный)
(defun sht:ctb-list ( / r res mask)
  (setq mask (if (= (getvar "PSTYLEMODE") 0) "*`.STB" "*`.CTB")
        r    (vl-catch-all-apply 'vlax-invoke (list (sht:model-layout) 'GetPlotStyleTableNames)))
  (if (and r (not (vl-catch-all-error-p r)))
    (foreach s r
      (if (and (= (type s) 'STR) (wcmatch (strcase s) mask) (not (member s res)))
        (setq res (cons s res)))))
  (setq res (vl-sort res '(lambda (a b) (< (strcase a) (strcase b)))))
  (if res res (list (if (= (getvar "PSTYLEMODE") 0) "monochrome.stb" "monochrome.ctb"))))

;; Стиль по умолчанию: прошлый выбор (реестр SHT_PCtb), иначе monochrome, иначе первый
(defun sht:ctb-default (lst / s r)
  (setq s (getenv "SHT_PCtb"))
  (cond
    ((and s (setq r (sht:find-ci s lst))) r)
    ((setq r (sht:find-ci (if (= (getvar "PSTYLEMODE") 0) "monochrome.stb" "monochrome.ctb") lst)) r)
    (t (car lst))))

;; Точка для SetWindowToPlot (массив из двух чисел)
(defun sht:pt2 (x y)
  (vlax-make-variant
    (vlax-safearray-fill (vlax-make-safearray vlax-vbDouble '(0 . 1)) (list (float x) (float y)))))

;; Массив ActiveX (safearray или variant с ним) -> список; не вышло — nil
(defun sht:sa (v / r)
  (if (= (type v) 'VARIANT) (setq v (vlax-variant-value v)))
  (setq r (vl-catch-all-apply 'vlax-safearray->list (list v)))
  (if (vl-catch-all-error-p r) nil r))

;; Числа в строке: "ISO_full_bleed_A3_(420.00_x_297.00_MM)" -> (3.0 420.0 297.0)
(defun sht:str-nums (s / i c tok res)
  (setq i   1
        tok ""
        s   (strcat s " "))
  (while (<= i (strlen s))
    (setq c (substr s i 1)
          i (1+ i))
    (cond
      ((wcmatch c "#") (setq tok (strcat tok c)))
      ((and (= c ".") (/= tok "") (not (vl-string-search "." tok))) (setq tok (strcat tok c)))
      (t
       (if (and (/= tok "") (distof tok 2)) (setq res (cons (distof tok 2) res)))
       (setq tok ""))))
  (reverse res))

;; Размер (a b) против листа w x h: 0 — так же, 1 — повёрнут на 90°, nil — другой
(defun sht:wh-match (a b w h)
  (cond
    ((and (< (abs (- a w)) 0.6) (< (abs (- b h)) 0.6)) 0)
    ((and (< (abs (- a h)) 0.6) (< (abs (- b w)) 0.6)) 1)))

;; Бумага плоттера для листа w x h мм у набора pc: (каноническое-имя поворот поля) или nil.
;; Кандидаты — по двум последним числам имени (не нашлось — все); размер и поля — у плоттера.
;; Лучше: поля не больше 0,6 мм (иначе край листа обрежется), затем — без поворота.
(defun sht:media-find (pc names w h / cand best lst r pw ph ll ur mg rot sc)
  (foreach nm names
    (setq lst (sht:str-nums nm))
    (if (and (>= (length lst) 2) (sht:wh-match (nth (- (length lst) 2) lst) (last lst) w h))
      (setq cand (cons nm cand))))
  (foreach nm (if cand (reverse cand) names)
    (setq pw nil ph nil ll nil ur nil mg 0.0
          r  (vl-catch-all-apply 'vla-put-CanonicalMediaName (list pc nm)))
    (if (not (vl-catch-all-error-p r))
      (setq r (vl-catch-all-apply 'vla-GetPaperSize (list pc 'pw 'ph))))
    (if (and (not (vl-catch-all-error-p r)) (numberp pw) (numberp ph) (setq rot (sht:wh-match pw ph w h)))
      (progn
        (setq r (vl-catch-all-apply 'vla-GetPaperMargins (list pc 'll 'ur)))
        (if (and (not (vl-catch-all-error-p r)) (setq lst (append (sht:sa ll) (sht:sa ur))))
          (setq mg (apply 'max (mapcar 'abs lst))))
        (setq sc (+ (if (> mg 0.6) 1000.0 0.0) (* rot 10.0) mg))
        (if (or (not best) (< sc (car best)))
          (setq best (list sc nm rot mg))))))
  (if best (cdr best)))

;; То же с запоминанием по размеру (sht:pcache — локальная переменная sht:plot-run)
(defun sht:media-cached (pc names w h / key p)
  (setq key (list w h))
  (if (setq p (assoc key sht:pcache))
    (cdr p)
    (cdar (setq sht:pcache (cons (cons key (sht:media-find pc names w h)) sht:pcache)))))

;; Общий набор: плоттер, стиль печати, веса линий
(defun sht:pc-new (name ctb / pc)
  (setq pc (vla-Add (sht:pcs) name :vlax-true))      ; набор для листа модели
  (vla-put-ConfigName pc *sht:Pc3*)
  (vla-RefreshPlotDeviceInfo pc)
  (vla-put-PaperUnits pc 1)                          ; acMillimeters
  (vla-put-PlotRotation pc 0)                        ; ac0degrees
  (vla-put-PlotWithPlotStyles pc :vlax-true)
  (vla-put-StyleSheet pc ctb)
  (vla-put-PlotWithLineweights pc :vlax-true)
  (vla-put-PlotHidden pc :vlax-false)
  (vla-put-CenterPlot pc :vlax-true)
  pc)

;; Настроить печать obj — параметры листа модели или набор — напрямую (s0.3.2: без CopyFrom — у Артёма
;; в s0.3 окно и масштаб через CopyFrom не доходили до печати): DWG To PDF, бумага m = (имя поворот поля),
;; стиль ctb, веса линий, окно = лист it в модели (экранные координаты), 1:масштаб, по центру.
;; Возвращает заданное окно ((x1 y1) (x2 y2)) — для обратной проверки.
(defun sht:plot-setup (obj it m ctb / p sc p1 p2 a b)
  (setq p  (nth 6 it)
        sc (nth 5 it)
        p1 (trans p 0 2)
        p2 (trans (list (+ (car p) (* sc (nth 7 it))) (+ (cadr p) (* sc (nth 8 it)))
                        (if (caddr p) (caddr p) 0.0))
                  0 2)
        a  (list (min (car p1) (car p2)) (min (cadr p1) (cadr p2)))
        b  (list (max (car p1) (car p2)) (max (cadr p1) (cadr p2))))
  (vla-put-ConfigName obj *sht:Pc3*)
  (vla-RefreshPlotDeviceInfo obj)
  (vla-put-CanonicalMediaName obj (car m))
  (vla-put-PaperUnits obj 1)                         ; acMillimeters
  (vla-put-PlotRotation obj (cadr m))                ; 0 — ac0degrees, 1 — ac90degrees
  (vla-put-PlotWithPlotStyles obj :vlax-true)
  (vla-put-StyleSheet obj ctb)
  (vla-put-PlotWithLineweights obj :vlax-true)
  (vla-put-PlotHidden obj :vlax-false)
  (vla-SetWindowToPlot obj (sht:pt2 (car a) (cadr a)) (sht:pt2 (car b) (cadr b)))
  (vla-put-PlotType obj 4)                           ; acWindow — только после окна
  (vla-put-UseStandardScale obj :vlax-false)
  (vla-SetCustomScale obj 1.0 (float sc))
  (vla-put-CenterPlot obj :vlax-true)
  (list a b))

;; Обратная проверка: что AutoCAD записал в obj. win — заданное окно, sc — масштаб листа.
;; Возвращает (годится строка-для-журнала)
(defun sht:plot-readback (obj win sc / ty st a b n d ok r)
  (setq ty (vl-catch-all-apply 'vla-get-PlotType (list obj))
        st (vl-catch-all-apply 'vla-get-UseStandardScale (list obj))
        r  (vl-catch-all-apply 'vla-GetWindowToPlot (list obj 'a 'b)))
  (if (vl-catch-all-error-p r)
    (setq a nil b nil)
    (setq a (sht:sa a)
          b (sht:sa b)))
  (if (vl-catch-all-error-p (vl-catch-all-apply 'vla-GetCustomScale (list obj 'n 'd)))
    (setq n nil d nil))
  (setq ok (and (equal ty 4) (eq st :vlax-false) a b (numberp n) (numberp d) (> n 0)
                (equal (/ d n) sc 1e-6)
                (equal (car a) (car (car win)) 1.0) (equal (cadr a) (cadr (car win)) 1.0)
                (equal (car b) (car (cadr win)) 1.0) (equal (cadr b) (cadr (cadr win)) 1.0)))
  (list ok
        (strcat "записано: "
                (cond ((equal ty 4) "окно") ((equal ty 0) "экран") ((equal ty 1) "границы")
                      ((equal ty 2) "лимиты") ((numberp ty) (itoa ty)) (t "?"))
                (if (and a b) (strcat " " (sht:n2s (car a)) "," (sht:n2s (cadr a)) " - " (sht:n2s (car b)) "," (sht:n2s (cadr b))) "")
                ", масштаб "
                (cond ((eq st :vlax-true) "стандартный (вписать?)")
                      ((and (numberp n) (numberp d) (> n 0)) (strcat "1:" (sht:n2s (/ d n))))
                      (t "?")))))

;; Область печати листа модели (CopyFrom может её не вернуть): (тип низ-лево верх-право стандартный
;; стандартный-масштаб числитель знаменатель) — запомнить до печати и вернуть после (*sht:ModelArea*)
(defun sht:model-area-get (lay / a b n d)
  (vl-catch-all-apply 'vla-GetWindowToPlot (list lay 'a 'b))
  (vl-catch-all-apply 'vla-GetCustomScale (list lay 'n 'd))
  (list (vl-catch-all-apply 'vla-get-PlotType (list lay)) (sht:sa a) (sht:sa b)
        (vl-catch-all-apply 'vla-get-UseStandardScale (list lay))
        (vl-catch-all-apply 'vla-get-StandardScale (list lay)) n d))

(defun sht:model-area-set (lay v)
  (if (and (= (length (nth 1 v)) 2) (= (length (nth 2 v)) 2))
    (vl-catch-all-apply 'vla-SetWindowToPlot
      (list lay (sht:pt2 (car (nth 1 v)) (cadr (nth 1 v))) (sht:pt2 (car (nth 2 v)) (cadr (nth 2 v))))))
  (if (numberp (car v)) (vl-catch-all-apply 'vla-put-PlotType (list lay (car v))))
  (if (and (numberp (nth 5 v)) (numberp (nth 6 v)) (> (nth 5 v) 0))
    (vl-catch-all-apply 'vla-SetCustomScale (list lay (nth 5 v) (nth 6 v))))
  (if (numberp (nth 4 v)) (vl-catch-all-apply 'vla-put-StandardScale (list lay (nth 4 v))))
  (if (member (nth 3 v) (list :vlax-true :vlax-false)) (vl-catch-all-apply 'vla-put-UseStandardScale (list lay (nth 3 v)))))

;; Запомнить параметры листа модели: копия SHT_PLOTSAVE (вернёт sht:pc-purge) и область печати
(defun sht:model-save ( / lay sv)
  (setq lay (sht:model-layout))
  (if (not (sht:pc-get *sht:PcSave*))
    (progn
      (setq sv (vla-Add (sht:pcs) *sht:PcSave* :vlax-true))
      (vla-CopyFrom sv lay)
      (setq *sht:ModelArea* (sht:model-area-get lay)))))

;; --- вывод ------------------------------------------------------------------

;; Список листов для PUBLISH (DSD): один PDF (Type=6). pairs — ((имя-листа . набор) …).
;; enc — "ansi" (кодировка Windows) или "utf8-bom". Возвращает fn или nil.
(defun sht:dsd-write (fn pairs pdf enc / f dwg lst)
  (setq dwg (strcat (getvar "DWGPREFIX") (getvar "DWGNAME"))
        f   (if (= enc "ansi") (open fn "w") (vl-catch-all-apply 'open (list fn "w" enc))))
  (if (vl-catch-all-error-p f) (setq f nil))
  (if f
    (progn
      (setq lst (list "[DWF6Version]" "Ver=1" "[DWF6MinorVersion]" "MinorVer=1"))
      (foreach p pairs
        (setq lst (append lst (list (strcat "[DWF6Sheet:" (car p) "]") (strcat "DWG=" dwg) "Layout=Model"
                                    (strcat "Setup=" (cdr p)) (strcat "OriginalSheetPath=" dwg)
                                    "Has Plot Port=0" "Has3DDWF=0"))))
      (setq lst (append lst
                  (list "[Target]" "Type=6" (strcat "DWF=" pdf) (strcat "OUT=" (vl-filename-directory pdf) "\\") "PWD="
                        "[PdfOptions]" "IncludeHyperlinks=TRUE" "CreateBookmarks=TRUE" "CaptureFontsInDrawing=TRUE"
                        "ConvertTextToGeometry=FALSE" "VectorResolution=1200" "RasterResolution=400"
                        "[AutoCAD Block Data]" "IncludeBlockInfo=0" "BlockTmplFilePath="
                        "[SheetSet Properties]" "IsSheetSet=FALSE" "IsHomogeneous=FALSE" "SheetSet Name="
                        "NoOfCopies=1" "PlotStampOn=FALSE" "ViewFile=FALSE" "JobID=0" "SelectionSetName="
                        (strcat "AcadProfile=" (if (getvar "CPROFILE") (getvar "CPROFILE") ""))
                        "CategoryName=" "LogFilePath=" "IncludeLayer=FALSE" "LineMerge=FALSE" "CurrentPrecision="
                        "PromptForDwfName=FALSE" "PwdProtectPublishedDWF=FALSE" "PromptForPwd=FALSE"
                        "RepublishingMarkups=FALSE" "DSTPath=" "PublishSheetSetMetadata=FALSE"
                        "PublishSheetMetadata=FALSE" "3DDWFOptions=0 1")))
      (foreach s lst (write-line s f))
      (close f)
      fn)))

;; Один PDF через -PUBLISH. Кодировка списка листов: сначала та, что сработала в прошлый раз
;; (реестр SHT_DsdEnc), не вышло — другая (ANSI / UTF-8 с BOM). T — файл pdf появился.
(defun sht:publish-all (pairs pdf / encs enc dsd log ok cnt)
  (setq encs (if (and (numberp (getvar "LISPSYS")) (> (getvar "LISPSYS") 0)) (list "ansi" "utf8-bom") (list "ansi")))
  (if (= (getenv "SHT_DsdEnc") "utf8-bom") (setq encs (reverse encs)))
  (while (and encs (not ok))
    (setq enc  (car encs)
          encs (cdr encs)
          dsd  (vl-filename-mktemp "shtpdf" nil ".dsd")
          log  (strcat (vl-filename-directory dsd) "\\" (vl-filename-base dsd) ".csv"))
    (if (sht:dsd-write dsd pairs pdf enc)
      (progn
        (princ (strcat "\nPUBLISH: листов " (itoa (length pairs)) " -> " pdf))
        (command "_.-PUBLISH" dsd)
        (setq cnt 0)
        (while (and (> (getvar "CMDACTIVE") 0) (< cnt 10))   ; лишние вопросы команды — по умолчанию
          (command "")
          (setq cnt (1+ cnt)))
        (if (setq ok (findfile pdf))
          (progn
            (setenv "SHT_DsdEnc" enc)
            (vl-file-delete dsd)
            (if (findfile log) (vl-file-delete log)))
          (princ (strcat "\nPUBLISH не создал PDF (список листов в кодировке " enc "): " dsd
                         (if (findfile log) (strcat "; журнал: " log) "")))))
      (princ (strcat "\nНе удалось записать список листов " dsd))))
  (if ok T))

;; Отдельные файлы: на каждый лист — параметры листа модели напрямую (sht:plot-setup), обратная проверка,
;; PlotToFile. jobs — ((лист бумага файл подпись) …). Прежние параметры модели вернёт sht:plot-cleanup.
;; Возвращает число файлов.
(defun sht:plot-each (jobs / lay plot n r q chk)
  (setq lay  (sht:model-layout)
        plot (vla-get-Plot (sht:doc))
        n    0)
  (sht:model-save)
  (setq q (vl-catch-all-apply 'vla-get-QuietErrorMode (list plot)))
  (vl-catch-all-apply 'vla-put-QuietErrorMode (list plot :vlax-true))
  (foreach j jobs
    (setq chk (sht:plot-readback lay (sht:plot-setup lay (car j) (cadr j) sht:pctb) (nth 5 (car j))))
    (princ (strcat "\n  " (cadddr j) ": " (cadr chk) (if (car chk) "" " - НЕ ТАК, как задано!")))
    (setq r (vl-catch-all-apply 'vla-PlotToFile (list plot (caddr j))))
    (if (and (not (vl-catch-all-error-p r)) (findfile (caddr j)))
      (progn
        (setq n (1+ n))
        (princ (strcat " -> " (vl-filename-base (caddr j)) ".pdf")))
      (princ (strcat " - НЕ НАПЕЧАТАН"
                     (if (vl-catch-all-error-p r) (strcat " (" (vl-catch-all-error-message r) ")") "")))))
  (if (not (vl-catch-all-error-p q)) (vl-catch-all-apply 'vla-put-QuietErrorMode (list plot q)))
  n)
;; Печать отмеченных в окне листов (переменные окна sht:p…). Возвращает число напечатанных.
(defun sht:plot-run ( / doc items dir all tag tpl names sht:pcache bad jobs k it m pc pcn chk nm fn used base pdf pairs lock n res)
  (setq doc   (sht:doc)
        items (sht:pick-items sht:psel)
        dir   sht:pdir
        all   (= sht:pmode "1")
        n     0)
  (setenv "SHT_PMode" sht:pmode)
  (setenv "SHT_PCtb" sht:pctb)
  (setenv "SHT_PSave" sht:psave)
  (setenv "SHT_POpen" sht:popen)
  (sht:plot-dir-save dir)
  (cond
    ((not (sht:mkdir dir))
     (alert (strcat "Не удалось создать папку для PDF:\n" dir)))
    (t
     ;; FILEDIA = 0: иначе -PUBLISH не берёт имя списка листов, а открывает окно выбора файла (s0.3.1)
     (sht:plot-sv-set (list (cons "CMDECHO" 0) (cons "FILEDIA" 0) (cons "BACKGROUNDPLOT" 0) (cons "PUBLISHCOLLATE" 1)
                            (cons "TILEMODE" 1)))
     (if (and (numberp (getvar "VIEWTWIST")) (not (equal (getvar "VIEWTWIST") 0.0 1e-9)))
       (princ "\nВНИМАНИЕ: вид в модели повёрнут (VIEWTWIST) - окна печати могут не совпасть с листами. Верните вид: _PLAN _World."))
     ;; ведомость листов и «Листов» (s0.5), тексты вписать в графы (как SHEET_UPDATE)
     (vla-StartUndoMark doc)
     (sht:sign-auto nil)                    ; подписи и логотип (s0.7)
     (sht:list-auto nil)
     (sht:fit-all)
     (vla-EndUndoMark doc)
     ;; имена наборов — свои у каждой печати (время): в сохранённом раньше файле таких нет
     (setq tag (strcat *sht:PcPrefix* (rtos (* 1e8 (rem (getvar "CDATE") 1.0)) 2 0) "_")
           tpl (vl-catch-all-apply 'sht:pc-new (list (strcat tag "000") sht:pctb)))
     (cond
       ((vl-catch-all-error-p tpl)
        (alert (strcat "Не удалось настроить печать на «" *sht:Pc3* "» со стилем «" sht:pctb "»:\n"
                       (vl-catch-all-error-message tpl))))
       (t
        (setq names (vlax-invoke tpl 'GetCanonicalMediaNames))
        ;; бумага каждому листу
        (foreach it items
          (setq m (sht:media-cached tpl names (nth 7 it) (nth 8 it)))
          (cond
            ((not (equal (cos (nth 9 it)) 1.0 1e-9))
             (setq bad (cons (strcat (sht:plot-sheet it) ": повёрнут - печатаются только неповёрнутые листы") bad)))
            ((not m)
             (setq bad (cons (strcat (sht:plot-sheet it) " (" (sht:plot-fmt it) "): у «" *sht:Pc3* "» нет бумаги "
                                     (sht:n2s (nth 7 it)) " x " (sht:n2s (nth 8 it)) " мм")
                             bad)))
            (t (setq jobs (cons (list it m) jobs)))))
        (setq jobs (reverse jobs))
        (cond
          (bad
           (alert (strcat "Печать не выполнена:\n" (sht:join (reverse bad) "\n")
                          "\n\nСнимите отметку с этих листов или исправьте их.")))
          (t
           ;; наборы параметров и имена
           (setq k    0
                 base (sht:plot-shifr items)
                 pdf  (strcat dir "\\" (sht:plot-file-all items)))
           (foreach j jobs
             (setq k    (1+ k)
                   it   (car j)
                   m    (cadr j)
                   nm   (sht:uniq-name (sht:dsd-name it) (mapcar 'car pairs))
                   fn   (sht:uniq-name (sht:plot-file-base it base) used)
                   used (cons fn used)
                   pcn  nil)
             (princ (strcat "\n" (sht:plot-sheet it) " (" (sht:plot-fmt it) "): бумага " (car m)
                            (if (= (cadr m) 1) ", поворот 90" "")))
             ;; один PDF — свой набор на лист, настроенный напрямую, с обратной проверкой
             (if all
               (progn
                 (setq pc  (vla-Add (sht:pcs) (strcat tag (sht:pad3 k)) :vlax-true)
                       pcn (vla-get-Name pc)
                       chk (sht:plot-readback pc (sht:plot-setup pc it m sht:pctb) (nth 5 it)))
                 (princ (strcat "; набор " pcn " - " (cadr chk) (if (car chk) "" " - НЕ ТАК, как задано!")))))
             (setq pairs (cons (list nm pcn (strcat dir "\\" fn ".pdf") it m) pairs)))
           (setq pairs (reverse pairs))
           ;; прежние файлы — удалить (занятый программой просмотра — не удалится)
           (foreach f (if all (list pdf) (mapcar 'caddr pairs))
             (if (findfile f) (vl-file-delete f))
             (if (findfile f) (setq lock (cons f lock))))
           (cond
             (lock
              (alert (strcat "Файл занят (открыт в программе просмотра?) - закройте его и повторите:\n"
                             (sht:join (reverse lock) "\n"))))
             (all
              (if (= sht:psave "1")
                (if (= (getvar "WRITESTAT") 0)
                  (princ "\nЧертёж открыт только для чтения - перед печатью не сохранён.")
                  (progn
                    (princ "\nСохранение чертежа перед печатью...")
                    (command "_.QSAVE"))))
              (if (sht:publish-all (mapcar '(lambda (p) (cons (car p) (cadr p))) pairs) pdf)
                (setq n   (length pairs)
                      res pdf)))
             (t
              (setq n   (sht:plot-each (mapcar '(lambda (p) (list (nth 3 p) (nth 4 p) (nth 2 p) (car p))) pairs))
                    res dir)))))))))
  (sht:plot-cleanup)
  (cond
    ((> n 0)
     (princ (strcat "\nНапечатано листов: " (itoa n) (if all (strcat " -> " res) (strcat ", папка " res))))
     (if (= sht:popen "1") (sht:open-path res)))
    (jobs (princ "\nPDF не получен - см. сообщения выше.")))
  (if sht:poff
    (princ (strcat "\nЛисты без номера не напечатаны: " (itoa (length sht:poff)) " (список выше).")))
  n)

;; --- окно «Печать в PDF» --------------------------------------------------------
;; Переменные окна (локальные в c:SHEET_PLOT): sht:pitems — листы с номером по порядку, sht:poff — без
;; номера, sht:psel — отмеченные (индексы), sht:pmode "1" один PDF / "0" отдельные, sht:pdir — папка,
;; sht:pctb / sht:pctbs — стиль и список, sht:psave sht:popen — "1"/"0", sht:pnums — поле «Номера»,
;; sht:pnums-ok — номера, по которым отмечено.

(defun sht:plot-init ()
  (start_list "sht_PList")
  (foreach it sht:pitems (add_list (sht:plot-line it)))
  (end_list)
  (set_tile "sht_PList" (sht:idx-str sht:psel))
  (sht:set-popup "sht_PCtb" sht:pctbs (vl-position sht:pctb sht:pctbs))
  (set_tile "sht_PMode" (if (= sht:pmode "0") "sht_PModeOne" "sht_PModeAll"))
  (set_tile "sht_PDir" sht:pdir)
  (set_tile "sht_PSave" sht:psave)
  (set_tile "sht_POpen" sht:popen)
  (set_tile "sht_PNums" sht:pnums)
  (set_tile "sht_POff" (sht:plot-off-str))
  (sht:plot-info)
  (action_tile "sht_PList" "(set_tile \"error\" \"\") (sht:plot-info)")
  (action_tile "sht_PAll" "(sht:plot-mark T)")
  (action_tile "sht_PNone" "(sht:plot-mark nil)")
  (action_tile "sht_PNums" "(if (member $reason '(1 2)) (sht:plot-on-nums))")
  (action_tile "sht_PNumsGo" "(sht:plot-on-nums)")
  (action_tile "sht_PSel" "(sht:plot-keep) (done_dialog 4)")
  (action_tile "sht_PDirB" "(sht:plot-keep) (done_dialog 3)")
  (action_tile "sht_PMode" "(sht:plot-info)")
  (action_tile "accept" "(sht:plot-ok)"))

;; Запомнить состояние окна (перед закрытием)
(defun sht:plot-keep ( / i)
  (setq sht:psel  (sht:idx-read (get_tile "sht_PList"))
        sht:pmode (if (= (get_tile "sht_PMode") "sht_PModeOne") "0" "1")
        sht:pdir  (sht:dir-norm (get_tile "sht_PDir"))
        i         (atoi (get_tile "sht_PCtb"))
        sht:pctb  (if (nth i sht:pctbs) (nth i sht:pctbs) (car sht:pctbs))
        sht:psave (get_tile "sht_PSave")
        sht:popen (get_tile "sht_POpen")
        sht:pnums (get_tile "sht_PNums")))

;; Строки окна: сколько отмечено, какое имя файла получится
(defun sht:plot-info ( / sel one)
  (setq sel (sht:idx-read (get_tile "sht_PList"))
        one (= (get_tile "sht_PMode") "sht_PModeOne"))
  (set_tile "sht_PCount" (strcat "Отмечено листов: " (itoa (length sel)) " из " (itoa (length sht:pitems))))
  (set_tile "sht_PFile"
    (cond
      ((not sel) "")
      (one (strcat "Файлы: " (sht:plot-file-one (nth (car sel) sht:pitems) (sht:plot-shifr (sht:pick-items sel)))
                   (if (cdr sel) ", ..." "")))
      (t (strcat "Файл: " (sht:plot-file-all (sht:pick-items sel))))))
  (mode_tile "sht_PSave" (if one 1 0)))

;; «Все» / «Ни одного»
(defun sht:plot-mark (all)
  (set_tile "sht_PList" (if all (sht:idx-str (sht:range 0 (length sht:pitems))) ""))
  (set_tile "error" "")
  (sht:plot-info))

;; «Отметить» (и Enter в поле «Номера»)
(defun sht:plot-on-nums ( / s r)
  (setq s            (sht:trim (get_tile "sht_PNums"))
        sht:pnums-ok s)
  (if (/= s "")
    (progn
      (setq r (sht:nums-pick s sht:pitems))
      (set_tile "sht_PList" (sht:idx-str (car r)))
      (set_tile "error" (if (cadr r) (strcat "Нет листов: " (sht:join (cadr r) ", ")) ""))
      (sht:plot-info))))

;; «Печать»: номера вписаны, но не отмечены — сначала отметить и показать
(defun sht:plot-ok ( / s)
  (setq s (sht:trim (get_tile "sht_PNums")))
  (if (and (/= s "") (/= s sht:pnums-ok))
    (progn
      (sht:plot-on-nums)
      (if (= (get_tile "error") "")
        (set_tile "error" "Листы отмечены по номерам - проверьте список и нажмите «Печать» ещё раз.")))
    (progn
      (sht:plot-keep)
      (cond
        ((not sht:psel) (set_tile "error" "Не отмечено ни одного листа."))
        ((= sht:pdir "") (set_tile "error" "Укажите папку для PDF."))
        ((and (= sht:pmode "1") (= (getvar "DWGTITLED") 0))
         (set_tile "error" "Чертёж ещё не сохранён: для одного PDF сохраните его (или выберите отдельные файлы)."))
        (t (done_dialog 1))))))

;; «...»: выбор папки (окно Windows); отказ или ошибка — папка прежняя
(defun sht:plot-browse ( / app sh hw f it p)
  (setq app (vlax-get-acad-object)
        sh  (vl-catch-all-apply 'vla-GetInterfaceObject (list app "Shell.Application")))
  (if (and sh (not (vl-catch-all-error-p sh)))
    (progn
      (setq hw (vl-catch-all-apply 'vla-get-HWND (list app))
            f  (vl-catch-all-apply 'vlax-invoke-method
                 (list sh 'BrowseForFolder (if (vl-catch-all-error-p hw) 0 hw) "Папка для PDF" 64)))
      (if (and f (not (vl-catch-all-error-p f)))
        (progn
          (setq it (vl-catch-all-apply 'vlax-get-property (list f 'Self)))
          (if (not (vl-catch-all-error-p it))
            (setq p (vl-catch-all-apply 'vlax-get-property (list it 'Path))))
          (if (and (= (type p) 'STR) (/= p "") (not (wcmatch p "::*")))
            (setq sht:pdir (sht:dir-norm (vl-string-translate "/" "\\" p))))
          (vl-catch-all-apply 'vlax-release-object (list f))))
      (vl-catch-all-apply 'vlax-release-object (list sh)))
    (princ "\nОкно выбора папки недоступно - впишите путь в поле «Папка».")))

;; «Выбрать в чертеже <»
(defun sht:plot-pick ( / ss i en k res)
  (princ "\nВыберите листы для печати (рамка или штамп листа), Enter - конец выбора: ")
  (if (setq ss (ssget '((0 . "INSERT") (2 . "SHT_*"))))
    (progn
      (setq i 0)
      (while (< i (sslength ss))
        (setq en (ssname ss i)
              i  (1+ i)
              k  0)
        (foreach it sht:pitems
          (if (eq (car it) en) (setq res (cons k res)))
          (setq k (1+ k))))
      (if res
        (setq sht:psel     (sht:uniq-sort res)
              sht:pnums    ""
              sht:pnums-ok "")
        (princ "\nСреди выбранного нет листов с номером."))))
  (princ))

;; Окно целиком. 1 — печать, 0 — отмена; «Выбрать в чертеже <» (4) и «...» (3) — окно открывается снова
(defun sht:plot-dialog ( / dcl_id dclFile ret)
  (setq ret 2)
  (if (sht:dlg-load)
    (while (> ret 1)
      (if (new_dialog "sht_plot" dcl_id)
        (progn
          (sht:plot-init)
          (setq ret (start_dialog))
          (cond
            ((= ret 3) (sht:plot-browse))
            ((= ret 4) (sht:plot-pick))))
        (progn
          (princ "\nSHEETS: не удалось открыть окно.")
          (setq ret 0))))
    (setq ret 0))
  (sht:dlg-cleanup)
  ret)

(defun c:SHEET_PLOT ( / *error* doc sdat r ens
                        sht:pitems sht:poff sht:psel sht:pdir sht:pmode sht:pctb sht:pctbs
                        sht:psave sht:popen sht:pnums sht:pnums-ok)
  (defun *error* (msg)
    (sht:plot-cleanup)
    (if (not (wcmatch (strcase msg) "*CANCEL*,*BREAK*,*ОТМЕН*,*ПРЕРВ*"))
      (princ (strcat "\nSHEETS: печать прервана: " msg)))
    (princ))
  (setq doc  (sht:doc)
        sdat (sht:prepare))
  (sht:dblclick-setup)
  (sht:plot-cleanup)                      ; остатки прошлой печати (после сбоя)
  (setq ens (sht:plot-presel0))           ; выбранное до команды
  (vla-StartUndoMark doc)
  (sht:apply-props)                       ; FORMAT / ORIENT из «Свойств» — до печати
  (vla-EndUndoMark doc)
  (setq r          (sht:plot-items)
        sht:pitems (car r)
        sht:poff   (cadr r))
  (sht:plot-warn-off)
  (cond
    ((not (or sht:pitems sht:poff))
     (princ "\nЛистов SHEETS в модели нет - печатать нечего."))
    ((not sht:pitems)
     (princ "\nУ всех листов пустой номер - печатать нечего (номер - в окне листа, двойной щелчок по листу)."))
    (t
     (setq sht:psel     (sht:plot-presel ens)
           sht:pctbs    (sht:ctb-list)
           sht:pctb     (sht:ctb-default sht:pctbs)
           sht:pmode    (if (= (getenv "SHT_PMode") "0") "0" "1")
           sht:psave    (if (= (getenv "SHT_PSave") "0") "0" "1")
           sht:popen    (if (= (getenv "SHT_POpen") "0") "0" "1")
           sht:pdir     (sht:plot-dir-load sdat)
           sht:pnums    ""
           sht:pnums-ok "")
     (if (= (sht:plot-dialog) 1) (sht:plot-run))))
  (sht:watch)
  (princ))

;;; --------------------------------------------------------------------------
;;;  14. ВЕДОМОСТЬ РАБОЧИХ ЧЕРТЕЖЕЙ (s0.5): SHEET_LIST
;;;  Таблица AutoCAD по образцу СПДС (так же, как спецификации PYLON_BASE): строка 0 — заголовок
;;;  над таблицей (без рамки сверху и по бокам), 1 — шапка «Лист / Наименование / Примечание»,
;;;  дальше — листы с номером по порядку номеров (как печать). Столбцы 15 / 140 / 30, шапка 15,
;;;  строки 8 (длинное наименование — строка сама становится выше), текст 2,5, заголовок 3,5 мм листа;
;;;  рамка, шапка и вертикали 0,7, между строками 0,2. Слой 0000_Таблицы.
;;;  Метка таблицы — XData SHT_TABLE: "LIST" и масштаб. Обновление — на месте: строки добавляются
;;;  и удаляются, тексты пишутся, только если поменялись (чертёж зря не становится «изменённым»);
;;;  заголовок меняется только из окна SHEET_LIST (правку заголовка в самой таблице не трогаем).
;;;  «Примечание» — по последнему изменению в штампе листа (sht:note).
;;;  «Листов» (графа 8) — число листов с номером, на первом по порядку листе; на остальных — пусто.
;;;  Вставка (s0.6.2, решение Артёма) — кликом, точка — левый верхний угол всей таблицы, верх строки
;;;  заголовка (к рамке листа), как у ведомости спецификаций; до s0.6.2 — угол рамки, заголовок над ним.
;;;  Автообновление (вкл. по умолчанию; в словаре чертежа @LISTAUTO = "0" — выкл.): перед сохранением
;;;  и печатью (реактор команд), в конце SHEET_NEW, окна «Лист», SHEET_PLOT; SHEET_UPDATE — всегда.
;;; --------------------------------------------------------------------------

(setq *sht:LayTbl*     "0000_Таблицы"     ; слой таблиц (как у PYLON_BASE)
      *sht:ListApp*    "SHT_TABLE"        ; XData-метка таблиц SHEETS
      *sht:ListTitle*  "Ведомость рабочих чертежей основного комплекта"
      *sht:ListHead*   '("Лист" "Наименование" "Примечание")
      *sht:ListCols*   '(15.0 140.0 30.0)
      *sht:ListTitleH* 11.25              ; строка заголовка: текст 3,5 по середине — низ текста в 3,9
                                          ; над рамкой, как в образце
      *sht:ListHeadH*  15.0
      *sht:ListRowH*   8.0
      *sht:ListTxt*    2.5                ; шапка и строки
      *sht:ListTitTxt* 3.5                ; заголовок
      *sht:ListLwBold* 70                 ; рамка, шапка, вертикали
      *sht:ListLwThin* 20                 ; между строками
      *sht:ListCmds*   '("QSAVE" "SAVE" "SAVEAS" "PLOT" "-PLOT" "PUBLISH" "-PUBLISH" "EXPORTPDF" "ETRANSMIT"))

;; --- «Примечание» ----------------------------------------------------------------

;; Номер изменения из графы «Изм.»: первые цифры ("2", "Изм.2" -> 2); цифр нет — 0
(defun sht:izm-n (s / i n c)
  (setq i 1 n 0)
  (while (and (<= i (strlen s)) (not (wcmatch (substr s i 1) "#")))
    (setq i (1+ i)))
  (while (and (<= i (strlen s)) (wcmatch (setq c (substr s i 1)) "#"))
    (setq n (+ (* n 10) (atoi c))
          i (1+ i)))
  n)

;; «Примечание» ведомости по штампу листа (решения Артёма, s0.5): последнее изменение — строка
;; с наибольшим № в графе «Изм.» (равные — верхняя, она позже); запись «Изм.N», по графе «Лист»:
;; «-» или пусто — без добавки, «Зам.» -> «Изм.N(зам.)», «Нов.» -> «Изм.N(нов.)», другое — так же,
;; строчными в скобках. a — атрибуты листа, n — строк изменений в штампе (форма 3 — 4, форма 6 — 2).
(defun sht:note (a n / i izm z best bz lst)
  (setq i 1)
  (repeat n
    (setq izm (sht:trim (cdr (assoc (strcat "C" (itoa i) "IZM") a))))
    (if (/= izm "")
      (progn
        (setq z (sht:izm-n izm))
        (if (or (not best) (>= z bz))
          (setq best i
                bz   z))))
    (setq i (1+ i)))
  (if best
    (progn
      (setq izm (sht:trim (cdr (assoc (strcat "C" (itoa best) "IZM") a)))
            lst (sht:trim (cdr (assoc (strcat "C" (itoa best) "LST") a))))
      (strcat (if (wcmatch izm "#*") (strcat "Изм." izm) izm)
              (if (member lst '("" "-" "–" "—")) "" (strcat (chr 40) (strcase lst T) (chr 41)))))
    ""))

;; Строк изменений в штампе формы: 3, 4 — 4; 5, 6 — 2 (s0.10)
(defun sht:chg-rows (form) (if (member (sht:fbase form) '("3" "4")) 4 2))

;; Листы для ведомости: (с-номером-по-порядку без-номера). Лист — (ename номер наименование
;; примечание форма масштаб точка): номер и точка — на тех же местах, что в sht:plot-item (sht:item<).
;; s0.10 (решение Артёма): в ведомость листов — только листы формы 3.
(defun sht:list-items ( / a inf it on off)
  (foreach en (sht:sheets)
    (setq inf (sht:sheet-info en))
    (if (= (sht:fbase (caddr inf)) "3")
      (progn
        (setq a  (sht:attrs en)
              it (list en (sht:trim (cdr (assoc "SHEET" a))) (sht:plain (cdr (assoc "TITLE" a)))
                       (sht:note a (sht:chg-rows (caddr inf))) (caddr inf) (cadddr inf) (nth 4 inf)))
        (if (= (nth 1 it) "")
          (setq off (cons it off))
          (setq on (cons it on))))))
  (list (vl-sort on 'sht:item<) (reverse off)))

;; Документы форм 4 и 5 (s0.10): ((обозначение (лист …)) …) — по обозначению (sht:nat<), листы
;; документа — по номерам (без номера — в конце); лист — как у ведомости листов (ename номер
;; наименование примечание форма масштаб точка). Документ — листы с одинаковой графой 1 (OBOZN; без
;; учёта регистра и пробелов по краям).
(defun sht:doc-items ( / a inf it key p res)
  (foreach en (sht:sheets)
    (setq inf (sht:sheet-info en))
    (if (sht:fdoc-p (caddr inf))
      (progn
        (setq a   (sht:attrs en)
              it  (list en (sht:trim (cdr (assoc "SHEET" a))) (sht:plain (cdr (assoc "TITLE" a)))
                        "" (caddr inf) (cadddr inf) (nth 4 inf))
              key (sht:plain (cdr (assoc "OBOZN" a))))
        (if (setq p (vl-some '(lambda (d) (if (= (car d) (sht:lc key)) d)) res))
          (setq res (subst (list (car p) (cadr p) (cons it (caddr p))) p res))
          (setq res (cons (list (sht:lc key) key (list it)) res))))))
  (setq res (mapcar '(lambda (d) (list (cadr d) (vl-sort (caddr d) 'sht:item<))) res))
  (vl-sort res '(lambda (x y) (sht:nat< (car x) (car y)))))

;; Наименование документа: графа 5 первого по порядку листа (пустая — следующего)
(defun sht:doc-name (d / s)
  (setq s "")
  (foreach it (cadr d) (if (= s "") (setq s (nth 2 it))))
  s)

;; --- таблица AutoCAD: вызовы через vlax-invoke (как PYLON_BASE); ошибка вызова не обрывает работу ---
(defun sht:tbl-do (tbl m args) (vl-catch-all-apply 'vlax-invoke (append (list tbl m) args)))
(defun sht:tbl-put (tbl p v) (vl-catch-all-apply 'vlax-put-property (list tbl p v)))

(defun sht:tbl-get (tbl p / r)
  (setq r (vl-catch-all-apply 'vlax-get (list tbl p)))
  (if (vl-catch-all-error-p r) nil r))

(defun sht:tbl-text (tbl r c / s)
  (setq s (sht:tbl-do tbl 'GetText (list r c)))
  (if (= (type s) 'STR) s ""))

;; Метка таблицы SHEETS (XData SHT_TABLE): (вид масштаб) или nil
(defun sht:tbl-mark (en / xd)
  (setq xd (cdr (assoc *sht:ListApp* (cdr (assoc -3 (entget en (list *sht:ListApp*)))))))
  (if xd (list (cdr (assoc 1000 xd)) (cdr (assoc 1040 xd)))))

(defun sht:tbl-mark-set (tbl kind sc / en)
  (regapp *sht:ListApp*)
  (vl-catch-all-apply 'vla-SetXData
    (list tbl
          (vlax-make-variant
            (vlax-safearray-fill (vlax-make-safearray vlax-vbInteger '(0 . 2)) '(1001 1000 1040)))
          (vlax-make-variant
            (vlax-safearray-fill (vlax-make-safearray vlax-vbVariant '(0 . 2))
                                 (list *sht:ListApp* kind (float sc))))))
  (setq en (vlax-vla-object->ename tbl))
  (if (not (sht:tbl-mark en))
    (vl-catch-all-apply 'entmod
      (list (list (cons -1 en) (list -3 (list *sht:ListApp* (cons 1000 kind) (cons 1040 (float sc))))))))
  (sht:tbl-mark en))

;; Таблицы SHEETS вида kind в чертеже (модель и листы бумаги; копии — тоже):
;; "LIST" — ведомость листов, "SPEC" — ведомость спецификаций (s0.6), "REFS" — ведомость ссылочных
;; и прилагаемых документов (s0.10)
(defun sht:kind-tables (kind / ss i en res)
  (if (setq ss (ssget "_X" (list '(0 . "ACAD_TABLE") (list -3 (list *sht:ListApp*)))))
    (progn
      (setq i 0)
      (while (< i (sslength ss))
        (setq en (ssname ss i)
              i  (1+ i))
        (if (= (car (sht:tbl-mark en)) kind)
          (setq res (cons (vlax-ename->vla-object en) res))))))
  (reverse res))

;; Таблицы ведомости листов
(defun sht:list-tables () (sht:kind-tables "LIST"))

;; Вид таблицы SHEETS по метке; столбцы и шапка вида (s0.10: "REFS" — ведомость ссылочных
;; и прилагаемых документов 60 / 95 / 30, остальные — 15 / 140 / 30)
(defun sht:tbl-kind (tbl) (car (sht:tbl-mark (vlax-vla-object->ename tbl))))
(defun sht:kind-cols (kind) (if (= kind "REFS") *sht:RefCols* *sht:ListCols*))
(defun sht:kind-head (kind) (if (= kind "REFS") *sht:RefHead* *sht:ListHead*))

(defun sht:tbl-scale (tbl / sc)
  (setq sc (cadr (sht:tbl-mark (vlax-vla-object->ename tbl))))
  (if (and (numberp sc) (> sc 0)) sc 1.0))

;; Оформление ведомости в масштабе sc: столбцы, высоты строк, текст, выравнивание, линии
(defun sht:tbl-format (tbl sc / n i nc r bad kind)
  (setq n    (sht:tbl-get tbl 'Rows)
        kind (sht:tbl-kind tbl))
  (sht:tbl-put tbl 'Layer *sht:LayTbl*)
  (sht:tbl-put tbl 'FlowDirection 0)                        ; сверху вниз
  (sht:tbl-put tbl 'TitleSuppressed :vlax-false)
  (sht:tbl-put tbl 'HeaderSuppressed :vlax-false)
  (sht:tbl-put tbl 'HorzCellMargin (* 1.5 sc))              ; наименование — в 1,5 мм от линии
  (sht:tbl-put tbl 'VertCellMargin (* 1.0 sc))
  (foreach rt '(1 2 4)                                      ; 1 данные, 2 заголовок, 4 шапка
    (sht:tbl-do tbl 'SetTextStyle (list rt *sht:Style*))
    (sht:tbl-do tbl 'SetAlignment (list rt 5)))             ; 5 — по центру
  (sht:tbl-do tbl 'SetTextHeight (list 2 (* *sht:ListTitTxt* sc)))
  (sht:tbl-do tbl 'SetTextHeight (list 4 (* *sht:ListTxt* sc)))
  (sht:tbl-do tbl 'SetTextHeight (list 1 (* *sht:ListTxt* sc)))
  (setq i 0)
  (foreach w (sht:kind-cols kind)
    (sht:tbl-do tbl 'SetColumnWidth (list i (* w sc)))
    (setq i (1+ i)))
  (sht:tbl-do tbl 'SetRowHeight (list 0 (* *sht:ListTitleH* sc)))
  (sht:tbl-do tbl 'SetRowHeight (list 1 (* *sht:ListHeadH* sc)))
  (setq i 2)
  (while (and (numberp n) (< i n))
    (sht:tbl-do tbl 'SetRowHeight (list i (* *sht:ListRowH* sc)))
    (sht:tbl-do tbl 'SetCellAlignment (list i 1 4))         ; наименование — влево, по середине
    (if (= kind "REFS")                                     ; s0.10: и обозначение
      (sht:tbl-do tbl 'SetCellAlignment (list i 0 4)))
    (setq i (1+ i)))
  ;; линии: 63 — все, 61 — все, кроме между строками (2); 0,7 — заголовок, шапка, рамка и вертикали
  (sht:tbl-do tbl 'SetGridLineWeight (list 63 2 *sht:ListLwBold*))
  (sht:tbl-do tbl 'SetGridLineWeight (list 63 4 *sht:ListLwBold*))
  (sht:tbl-do tbl 'SetGridLineWeight (list 61 1 *sht:ListLwBold*))
  (sht:tbl-do tbl 'SetGridLineWeight (list 2 1 *sht:ListLwThin*))
  ;; заголовок — без линий сверху и по бокам (s0.9). Как сделал Артём вручную («Границы ячеек»):
  ;; 1) «Без границ» — ВСЕ ячейки строки заголовка (объединённые A, B, C), все стороны: 63 = 1 верх
  ;;    + 2 между строками + 4 низ + 8 лево + 16 между столбцами + 32 право;
  ;; 2) «Все границы» — все ячейки шапки: её верх — это и есть низ заголовка (линия остаётся).
  ;; s0.5.1 выключал только ячейку (0,0) и три стороны — рамка над B, C и справа оставалась.
  ;; По типу строк (SetGridVisibility) — оставлено, у Артёма ничего не меняло. Ошибки — в *sht:GridErr*.
  (sht:tbl-do tbl 'SetGridVisibility (list 57 2 :vlax-false))
  (setq nc (length *sht:ListCols*))
  (foreach rv '((0 . :vlax-false) (1 . :vlax-true))
    (setq i 0)
    (while (< i nc)
      (setq r (sht:tbl-do tbl 'SetGridVisibility2 (list (car rv) i 63 (cdr rv))))
      (if (vl-catch-all-error-p r)
        (progn
          (if (not bad)                                     ; первая ошибка
            (setq bad (strcat "SetGridVisibility2 " (itoa (car rv)) "," (itoa i) ": "
                              (vl-catch-all-error-message r))))
          ;; запасной — прежний способ по ячейке (15 = все стороны)
          (sht:tbl-do tbl 'SetCellGridVisibility (list (car rv) i 15 (cdr rv)))))
      (setq i (1+ i))))
  ;; проверка: AutoCAD считает верх заголовка над B (0,1) видимым?
  (if (and (not bad) (> nc 0))
    (progn
      (setq r (sht:tbl-do tbl 'GetGridVisibility2 (list 0 1 1)))
      (if (and (not (vl-catch-all-error-p r)) (member r (list :vlax-true -1 T)))
        (setq bad "GetGridVisibility2 0,1: верх заголовка по-прежнему видим"))))
  (if (and bad (not *sht:GridErr*))
    (progn
      (setq *sht:GridErr* bad)
      (princ (strcat "\nSHEETS: рамка заголовка таблицы, возможно, не убрана - " bad
                     " (сообщите разработчику)."))))
  bad)

;; Строки таблицы под заголовком: шапка head, затем листы (номер наименование примечание);
;; листов нет — одна пустая строка
(defun sht:list-cells (items head / res)
  (foreach it items
    (setq res (cons (list (nth 1 it) (nth 2 it) (nth 3 it)) res)))
  (cons head (if res (reverse res) (list (list "" "" "")))))

;; Тексты таблицы (с 1-й строки) отличаются от cells? s0.10: сравнение без форматирования MText
;; (заголовки разделов ведомости ссылочных — подчёркнутые, «\L…\l»)
(defun sht:tbl-diff (tbl cells / r c d)
  (setq r 1)
  (foreach row cells
    (setq c 0)
    (foreach s row
      (if (and (not d) (/= (sht:mt-plain (sht:tbl-text tbl r c)) (sht:mt-plain s))) (setq d T))
      (setq c (1+ c)))
    (setq r (1+ r)))
  d)

;; Записать строки: число строк, оформление, тексты. T — строк столько, сколько нужно.
(defun sht:tbl-write (tbl sc cells title / n need r c k m)
  (setq n    (sht:tbl-get tbl 'Rows)
        need (1+ (length cells)))
  (cond
    ((< n need)          ; новые строки — перед последней (вставка внутрь таблицы надёжнее, чем в конец)
     (sht:tbl-do tbl 'InsertRows (list (if (> n 2) (1- n) n) (* *sht:ListRowH* sc) (- need n))))
    ((> n need)
     (sht:tbl-do tbl 'DeleteRows (list need (- n need)))
     ;; s0.5.1: не удалились разом — по одной с конца, пока число строк убывает
     (setq k (sht:tbl-get tbl 'Rows))
     (while (and (numberp k) (> k need)
                 (progn
                   (sht:tbl-do tbl 'DeleteRows (list (1- k) 1))
                   (setq m (sht:tbl-get tbl 'Rows))
                   (and (numberp m) (< m k))))
       (setq k m))))
  (sht:tbl-format tbl sc)
  (if title (sht:tbl-do tbl 'SetText (list 0 0 title)))
  (setq r 1)
  (foreach row cells
    (setq c 0)
    (foreach s row
      (sht:tbl-do tbl 'SetText (list r c s))
      (setq c (1+ c)))
    ;; s0.10: заголовок раздела ведомости ссылочных («\LПрилагаемые документы\l») — по центру
    (if (and (> r 1) (= (substr (cadr row) 1 2) "\\L"))
      (sht:tbl-do tbl 'SetCellAlignment (list r 1 5)))
    (setq r (1+ r)))
  (= (sht:tbl-get tbl 'Rows) need))

;; Привести таблицу к листам items. title — заголовок (nil — не трогать), force — оформление заново.
;; T — таблица менялась.
(defun sht:tbl-fill (tbl items title force / sc cells n r ch b)
  (setq sc    (sht:tbl-scale tbl)
        cells (sht:list-cells items (sht:kind-head (sht:tbl-kind tbl)))
        n     (sht:tbl-get tbl 'Rows))
  (setq ch
  (if (or force (not (numberp n)) (/= n (1+ (length cells)))
          (and title (/= (sht:tbl-text tbl 0 0) title))
          (sht:tbl-diff tbl cells))
    (progn
      (sht:tbl-put tbl 'RegenerateTableSuppressed :vlax-true)
      (setq r (vl-catch-all-apply 'sht:tbl-write (list tbl sc cells title)))
      (sht:tbl-put tbl 'RegenerateTableSuppressed :vlax-false)     ; всегда: иначе текст таблицы не виден
      (cond
        ((vl-catch-all-error-p r)
         (princ (strcat "\nSHEETS: ведомость не записана: " (vl-catch-all-error-message r))))
        ((not r)
         (princ "\nSHEETS: в таблице ведомости не то число строк - удалите её и вставьте заново (SHEET_LIST).")))
      T)))
  ;; s0.13: ниже рамки листа — разрыв на части
  (setq b (vl-catch-all-apply 'sht:tbl-break (list tbl)))
  (if (vl-catch-all-error-p b)
    (princ (strcat "\nSHEETS: разрыв ведомости не проверен: " (vl-catch-all-error-message b))))
  (or ch (= b T)))

;;; --------------------------------------------------------------------------
;;;  14а. РАЗРЫВ ВЕДОМОСТЕЙ ПО ВЫСОТЕ ЛИСТА (s0.13)
;;;  Таблица SHEETS (ведомость листов, спецификаций, ссылочных) стоит на листе SHEETS в модели и ниже
;;;  рамки листа не помещается — включается разрыв таблицы AutoCAD (одна таблица, части): высота части —
;;;  от верха таблицы до рамки поля (над основной надписью — до её верха, если часть заходит на неё
;;;  по ширине); части — вправо через *sht:BrkGap* мм листа; заголовок и шапка повторяются в каждой части;
;;;  части можно двигать ручкой (AllowManualPositions). Помещается снова — разрыв снимается.
;;;  Состояние — XData SHT_BREAK: 1040 высота части (0 — без разрыва), 1041 добавка к сумме высот строк
;;;  (строки с переносом, если GetRowHeight их не учитывает), 1070 частей. Проверка — при каждом
;;;  заполнении таблицы (sht:tbl-fill) и в конце команд (sht:watch-check: ведомость перенесли);
;;;  таблица меняется, только когда меняется высота части или число частей.
;;; --------------------------------------------------------------------------

(setq *sht:BrkApp* "SHT_BREAK"
      *sht:BrkGap* 10.0                  ; между частями, мм листа
      *sht:BrkTol* 0.5                   ; допуск, мм листа
      *sht:StampH* '(("3" . 55.0) ("4" . 55.0) ("5" . 40.0) ("6" . 15.0))
      *sht:BrkErr* nil)

;; Сохранённое состояние разрыва: (высота-части добавка частей); нет — (0.0 0.0 1)
(defun sht:brk-get (en / xd)
  (setq xd (cdr (assoc *sht:BrkApp* (cdr (assoc -3 (entget en (list *sht:BrkApp*)))))))
  (list (cond ((cdr (assoc 1040 xd))) (0.0))
        (cond ((cdr (assoc 1041 xd))) (0.0))
        (cond ((cdr (assoc 1070 xd))) (1))))

(defun sht:brk-put (tbl h ex n / en)
  (regapp *sht:BrkApp*)
  (vl-catch-all-apply 'vla-SetXData
    (list tbl
          (vlax-make-variant
            (vlax-safearray-fill (vlax-make-safearray vlax-vbInteger '(0 . 3)) '(1001 1040 1041 1070)))
          (vlax-make-variant
            (vlax-safearray-fill (vlax-make-safearray vlax-vbVariant '(0 . 3))
                                 (list *sht:BrkApp* (float h) (float ex) (vlax-make-variant n vlax-vbInteger))))))
  (setq en (vlax-vla-object->ename tbl))
  (if (not (equal (sht:brk-get en) (list (float h) (float ex) n) 1e-6))
    (vl-catch-all-apply 'entmod
      (list (list (cons -1 en)
                  (list -3 (list *sht:BrkApp* (cons 1040 (float h)) (cons 1041 (float ex)) (cons 1070 n)))))))
  (sht:brk-get en))

;; Низ, до которого может идти часть таблицы на листе sh: x — левый край части, w — её ширина
;; (единицы модели). Рамка поля снизу; часть заходит по ширине на основную надпись — верх надписи.
;; Возвращает (низ правый-край-рамки).
(defun sht:brk-floor (sh x w / inf wh sc q right bot)
  (setq inf   (sht:sheet-info sh)
        wh    (sht:fmt-wh (car inf) (cadr inf))
        sc    (cadddr inf)
        q     (nth 4 inf)
        right (+ (car q) (* sc (- (car wh) (caddr *sht:Margins*))))
        bot   (+ (cadr q) (* sc (cadr *sht:Margins*))))
  (if (and (> (+ x w) (+ (- right (* 185.0 sc)) (* *sht:BrkTol* sc)))
           (< x (- right (* *sht:BrkTol* sc))))
    (setq bot (+ bot (* sc (cond ((cdr (assoc (sht:fbase (caddr inf)) *sht:StampH*))) (55.0))))))
  (list bot right))

;; Высоты строк таблицы (GetRowHeight; не отдал — заданные программой)
(defun sht:tbl-rowhs (tbl sc / n i h res)
  (setq n (sht:tbl-get tbl 'Rows)
        i 0)
  (while (and (numberp n) (< i n))
    (setq h (sht:tbl-do tbl 'GetRowHeight (list i)))
    (if (not (numberp h))
      (setq h (* sc (cond ((= i 0) *sht:ListTitleH*) ((= i 1) *sht:ListHeadH*) (t *sht:ListRowH*)))))
    (setq res (cons (float h) res)
          i   (1+ i)))
  (reverse res))

;; Части при высоте части lim: (частей высота-второй-части); hs — высоты строк (заголовок, шапка, данные),
;; заголовок и шапка — в каждой части, в части не меньше одной строки данных
(defun sht:brk-parts (hs lim tol / lab cur parts h2)
  (setq lab   (+ (car hs) (cadr hs))
        cur   lab
        parts 1)
  (foreach h (cddr hs)
    (if (and (> (+ cur h) (+ lim tol)) (> cur (+ lab 1e-6)))
      (setq parts (1+ parts)
            cur   (+ lab h))
      (setq cur (+ cur h)))
    (if (= parts 2) (setq h2 cur)))
  (list parts h2))

(defun sht:kind-name (kind)
  (cond ((= kind "SPEC") "Ведомость спецификаций")
        ((= kind "REFS") "Ведомость ссылочных и прилагаемых документов")
        (t "Ведомость листов")))

(defun sht:parts-str (n)
  (strcat (itoa n) (if (< n 5) " части" " частей")))

;; Включить (h > 0) / снять разрыв. Ошибка — строка (первая), иначе nil.
(defun sht:brk-apply (tbl h sc / err r)
  (if (> h 0)
    (foreach pv (list (list 'EnableBreak) (cons 'RepeatTopLabels :vlax-true)
                      (cons 'AllowManualPositions :vlax-true) (cons 'TableBreakFlowDirection 1)
                      (cons 'BreakSpacing (* *sht:BrkGap* sc)) (cons 'TableBreakHeight h))
      (setq r (if (= (car pv) 'EnableBreak)
                (sht:tbl-do tbl 'EnableBreak (list :vlax-true))
                (sht:tbl-put tbl (car pv) (cdr pv))))
      (if (and (vl-catch-all-error-p r) (not err))
        (setq err (strcat (vl-symbol-name (car pv)) ": " (vl-catch-all-error-message r)))))
    (progn
      (setq r (sht:tbl-do tbl 'EnableBreak (list :vlax-false)))
      (if (vl-catch-all-error-p r)
        (setq err (strcat "EnableBreak: " (vl-catch-all-error-message r))))))
  err)

;; Разрыв таблицы SHEETS по высоте листа. T — разрыв включён / снят / изменился.
(defun sht:tbl-break (tbl / en ed p sh sc w tol old hs sum tot ex fr1 fr2 x2 lim1 lim2 pr parts h2 want
                            on err msg)
  (setq en    (vlax-vla-object->ename tbl)
        ed    (entget en)
        p     (cdr (assoc 10 ed))
        sc    (sht:tbl-scale tbl)
        w     (* sc (apply '+ (sht:kind-cols (sht:tbl-kind tbl))))
        tol   (* *sht:BrkTol* sc)
        old   (sht:brk-get en)
        on    (> (car old) 0)
        ex    (cadr old)
        want  0.0
        parts 1)
  (if (and (= (strcase (cond ((cdr (assoc 410 ed))) ("Model"))) "MODEL")
           (setq sh (car (sht:sheet-at p))))
    (progn
      (setq hs   (sht:tbl-rowhs tbl sc)
            sum  (apply '+ hs)
            fr1  (sht:brk-floor sh (car p) w)
            x2   (+ (car p) w (* *sht:BrkGap* sc))
            fr2  (sht:brk-floor sh x2 w)
            lim1 (- (cadr p) (car fr1))
            lim2 (- (cadr p) (car fr2)))
      ;; без разрыва — высота всей таблицы AutoCAD (строки с переносом): добавка к сумме высот строк
      (if (and (not on) (numberp (setq tot (sht:tbl-get tbl 'Height))))
        (setq ex (max 0.0 (- tot sum))))
      (if (and (> (length hs) 2)
               (> (+ sum ex) (+ lim1 tol))
               (>= lim1 (+ (car hs) (cadr hs) (caddr hs))))     ; хоть одна строка в части
        (setq pr    (sht:brk-parts hs lim1 tol)
              parts (max 2 (car pr))
              h2    (cadr pr)
              want  lim1))))
  (if (or (> (abs (- want (car old))) tol) (/= parts (caddr old)))
    (progn
      (if (> (abs (- want (car old))) tol)
        (setq err (sht:brk-apply tbl want sc)))
      (sht:brk-put tbl want ex parts)
      (setq msg (strcat "\nSHEETS: " (sht:kind-name (sht:tbl-kind tbl))))
      (cond
        ((> want 0)
         (princ (strcat msg " ниже рамки листа " (sht:sheet-no sh) " - разделена на "
                        (sht:parts-str parts) " (высота части " (sht:n2s (/ want sc)) " мм листа)."))
         (if (> parts 2)
           (princ "\n  В 2 части не помещается: третья и следующие части - тоже вправо, перенесите их ручкой."))
         (if (> (+ x2 w) (+ (cadr fr2) tol))
           (princ "\n  Вторая часть - правее рамки листа: перенесите её ручкой или поставьте ведомость левее."))
         (if (and h2 (> h2 (+ lim2 tol)))
           (princ "\n  Вторая часть заходит на основную надпись - перенесите её ручкой.")))
        (t (princ (strcat msg " помещается на листе - снова одна часть."))))
      (if err
        (progn
          (princ (strcat "\nSHEETS: разрыв таблицы не настроен - " err " (сообщите разработчику)."))
          (setq *sht:BrkErr* err)))
      T)))

;; Разрыв всех таблиц SHEETS (конец команды: ведомость перенесли). Число изменённых.
(defun sht:brk-all ( / ss i en r n)
  (setq n 0)
  (if (setq ss (ssget "_X" (list '(0 . "ACAD_TABLE") (list -3 (list *sht:ListApp*)))))
    (progn
      (setq i 0)
      (while (< i (sslength ss))
        (setq en (ssname ss i)
              i  (1+ i))
        (if (sht:tbl-mark en)
          (progn
            (setq r (vl-catch-all-apply 'sht:tbl-break (list (vlax-ename->vla-object en))))
            (cond
              ((vl-catch-all-error-p r)
               (princ (strcat "\nSHEETS: разрыв ведомости не проверен: " (vl-catch-all-error-message r))))
              ((= r T) (setq n (1+ n)))))))))
  n)

;; «Листов» (графа 8): на первом по порядку листе — число листов с номером, на остальных — пусто.
;; s0.10: документы форм 4, 5 — на первом листе документа число его листов (и без номера), на остальных
;; пусто. Возвращает число изменённых листов.
(defun sht:list-count (items / en1 v k inf docs)
  (setq en1 (car (car items))
        k   0)
  (foreach d (sht:doc-items)
    (setq docs (cons (cons (car (car (cadr d))) (itoa (length (cadr d)))) docs)))
  (foreach en (sht:sheets)
    (setq v (cond ((equal en en1) (itoa (length items)))
                  ((cdr (assoc en docs)))
                  ("")))
    (foreach a (sht:att-objs en)
      (if (and (= (strcase (vla-get-TagString a)) "SHEETS") (/= (vla-get-TextString a) v))
        (progn
          (setq inf (sht:sheet-info en)
                k   (1+ k))
          (sht:att-set a v (cadddr inf) (sht:attr-tab (caddr inf)))))))
  k)

;; Обновить все таблицы ведомости и «Листов». title — новый заголовок (nil — не трогать),
;; force — оформление заново. s0.6: затем — ведомость спецификаций (sht:spec-update, заголовок не трогает;
;; её ошибка ведомости листов не мешает). Возвращает
;; (таблиц-изменено таблиц-всего листов-с-номером «Листов»-изменено номер-первого-листа спецификации),
;; спецификации — итог sht:spec-update (nil — таблиц ведомости спецификаций нет).
(defun sht:list-update (title force / sdat items tbls nt nc sr rr)
  (setq sdat  (sht:set-read)
        items (car (sht:list-items))
        tbls  (sht:list-tables)
        nt    0
        nc    0)
  (foreach tbl tbls
    (if (sht:tbl-fill tbl items title force) (setq nt (1+ nt))))
  (if (/= (cdr (assoc "@LISTCNT" sdat)) "0")
    (setq nc (sht:list-count items)))
  (setq sr (vl-catch-all-apply 'sht:spec-update (list nil force)))
  (if (vl-catch-all-error-p sr)
    (progn
      (princ (strcat "\nSHEETS: ведомость спецификаций не обновлена: " (vl-catch-all-error-message sr)))
      (setq sr nil)))
  ;; s0.10: ведомость ссылочных и прилагаемых документов (7-й элемент итога)
  (setq rr (vl-catch-all-apply 'sht:refs-update (list nil force)))
  (if (vl-catch-all-error-p rr)
    (progn
      (princ (strcat "\nSHEETS: ведомость ссылочных документов не обновлена: " (vl-catch-all-error-message rr)))
      (setq rr nil)))
  (list nt (length tbls) (length items) nc (if items (nth 1 (car items))) sr rr))

;; Сообщение об обновлении; all — и когда таблицы не менялись
(defun sht:list-msg (r all)
  (if (or all (> (car r) 0))
    (princ (strcat "\nВедомость листов: листов с номером " (itoa (nth 2 r))
                   (cond ((= (cadr r) 0) " - таблицы ведомости в чертеже нет (вставить: SHEET_LIST)")
                         ((> (car r) 0) (strcat ", обновлено таблиц: " (itoa (car r)) " из " (itoa (cadr r))))
                         (t ", таблица без изменений"))
                   ".")))
  (if (> (nth 3 r) 0)
    (princ (strcat "\n«Листов» (графа 8): "
                   (if (nth 4 r) (strcat (itoa (nth 2 r)) " - на листе " (nth 4 r)) "пусто")
                   ", изменено листов: " (itoa (nth 3 r)) ".")))
  (if (nth 5 r) (sht:spec-msg (nth 5 r) nil))                   ; s0.6 — только если менялась
  (if (nth 6 r) (sht:refs-msg (nth 6 r) nil)))                  ; s0.10

;; Автообновление: в конце команд SHEETS и перед сохранением / печатью (реактор).
;; Ошибка не мешает команде; quiet — не писать (сообщение даст вызывающий). Возвращает итог или nil.
(defun sht:list-auto (quiet / r)
  (if (and (not *sht:ListBusy*) (/= (cdr (assoc "@LISTAUTO" (sht:set-read))) "0"))
    (progn
      (setq *sht:ListBusy* T
            r              (vl-catch-all-apply 'sht:list-update (list nil nil))
            *sht:ListBusy* nil)
      (cond
        ((vl-catch-all-error-p r)
         (princ (strcat "\nSHEETS: ведомость листов не обновлена: " (vl-catch-all-error-message r)))
         nil)
        (t
         (if (not quiet) (sht:list-msg r nil))
         r)))))

;; --- окно «Ведомость рабочих чертежей» -------------------------------------------
;; Переменные окна (локальные в c:SHEET_LIST): sht:litems sht:loff — листы с номером / без номера,
;; sht:ltbls — таблицы ведомости, sht:ltitle — заголовок, sht:lcnt sht:lauto — "1" / "0".

(defun sht:list-line (it)
  (strcat (nth 1 it) "\t" (nth 2 it) "\t" (nth 3 it)))

(defun sht:list-dups (items / seen res)
  (foreach it items
    (if (member (strcase (nth 1 it)) seen)
      (if (not (member (nth 1 it) res)) (setq res (cons (nth 1 it) res)))
      (setq seen (cons (strcase (nth 1 it)) seen))))
  (reverse res))

(defun sht:list-info ( / it1)
  (setq it1 (car sht:litems))
  (strcat "Листов с номером: " (itoa (length sht:litems))
          " (только листы формы 3). "
          (if sht:ltbls
            (strcat "Таблиц ведомости в чертеже: " (itoa (length sht:ltbls)) " - «Обновить» перепишет их.")
            "Таблицы ведомости в чертеже нет - «Вставить ведомость <».")))

(defun sht:list-off ( / s d)
  (setq s "")
  (if sht:loff
    (setq s (strcat "Без номера - не войдут (" (itoa (length sht:loff)) "): "
                    (sht:join (mapcar '(lambda (it) (if (= (nth 2 it) "") "(без наименования)" (strcat "«" (nth 2 it) "»")))
                                      sht:loff)
                              ", "))))
  (if (setq d (sht:list-dups sht:litems))
    (setq s (strcat (if (= s "") "" (strcat s ". ")) "Повторяются номера: " (sht:join d ", "))))
  (if (> (strlen s) 100) (strcat (substr s 1 97) "...") s))

(defun sht:list-init ()
  (start_list "sht_LList")
  (foreach it sht:litems (add_list (sht:list-line it)))
  (end_list)
  (set_tile "sht_LInfo" (sht:list-info))
  (set_tile "sht_LOff" (sht:list-off))
  (set_tile "sht_LTitle" sht:ltitle)
  (set_tile "sht_LCnt" sht:lcnt)
  (set_tile "sht_LAuto" sht:lauto)
  (action_tile "sht_LIns" "(sht:list-ok 2)")
  (action_tile "accept" "(sht:list-ok 1)"))

;; «Обновить» (1) / «Вставить ведомость <» (2)
(defun sht:list-ok (code)
  (setq sht:ltitle (sht:trim (get_tile "sht_LTitle"))
        sht:lcnt   (get_tile "sht_LCnt")
        sht:lauto  (get_tile "sht_LAuto"))
  (if (= sht:ltitle "")
    (set_tile "error" "Впишите заголовок ведомости.")
    (done_dialog code)))

(defun sht:list-dialog ( / dcl_id dclFile ret)
  (setq ret 0)
  (if (sht:dlg-load)
    (if (new_dialog "sht_list" dcl_id)
      (progn
        (sht:list-init)
        (setq ret (start_dialog)))
      (princ "\nSHEETS: не удалось открыть окно.")))
  (sht:dlg-cleanup)
  ret)

;; Настройки ведомости — в словарь чертежа (если поменялись)
(defun sht:list-save ( / sdat new)
  (setq sdat (sht:set-read)
        new  (sht:alist-put (sht:alist-put (sht:alist-put sdat "@LISTTITLE" sht:ltitle)
                                           "@LISTCNT" sht:lcnt)
                            "@LISTAUTO" sht:lauto))
  (if (not (equal new sdat)) (sht:set-write new)))

;; Лист SHEETS, на котором точка p (мировые координаты): (ename масштаб) или nil
(defun sht:sheet-at (p / inf wh q res)
  (foreach en (sht:sheets)
    (setq inf (sht:sheet-info en)
          wh  (sht:fmt-wh (car inf) (cadr inf))
          q   (nth 4 inf))
    (if (and (not res)
             (<= (car q) (car p) (+ (car q) (* (cadddr inf) (car wh))))
             (<= (cadr q) (cadr p) (+ (cadr q) (* (cadddr inf) (cadr wh)))))
      (setq res (list en (cadddr inf)))))
  res)

;; Точка не на листе — спросить масштаб (по умолчанию — как у первого листа)
(defun sht:list-ask-scale ( / d r)
  (setq d (cond ((nth 5 (car sht:litems))) (*sht_Scale*) (100.0)))
  (initget 6)
  (setq r (getreal (strcat "\nТочка не на листе SHEETS. Масштаб ведомости 1:<" (sht:n2s d) ">: ")))
  (if r r d))

;; Новая таблица ведомости вида kind ("LIST" / "SPEC", s0.6): pt — левый верхний угол всей таблицы
;; (верх строки заголовка), sc — масштаб
(defun sht:tbl-new (pt sc title kind / tbl)
  (sht:layer *sht:LayTbl*)
  (setq tbl (vlax-invoke (sht:ms) 'AddTable
                         (list (float (car pt)) (float (cadr pt)) 0.0)
                         3 3 (* *sht:ListRowH* sc) (* 20.0 sc)))
  (sht:tbl-mark-set tbl kind sc)
  (sht:tbl-put tbl 'RegenerateTableSuppressed :vlax-true)
  (sht:tbl-do tbl 'MergeCells (list 0 0 0 2))       ; заголовок обычно уже объединён стилем — ошибка не мешает
  (vl-catch-all-apply 'sht:tbl-format (list tbl sc))
  (sht:tbl-do tbl 'SetText (list 0 0 title))
  (sht:tbl-put tbl 'RegenerateTableSuppressed :vlax-false)
  tbl)

(defun c:SHEET_LIST ( / doc sdat d ret pt hit sc tbl r h
                        sht:litems sht:loff sht:ltbls sht:ltitle sht:lcnt sht:lauto)
  (setq doc  (sht:doc)
        sdat (sht:prepare))
  (sht:dblclick-setup)
  (sht:defaults)
  (setq d          (sht:list-items)
        sht:litems (car d)
        sht:loff   (cadr d)
        sht:ltbls  (sht:list-tables)
        sht:ltitle (cond ((and sht:ltbls (/= (sht:tbl-text (car sht:ltbls) 0 0) ""))
                          (sht:tbl-text (car sht:ltbls) 0 0))
                         ((/= (sht:trim (cdr (assoc "@LISTTITLE" sdat))) "")
                          (cdr (assoc "@LISTTITLE" sdat)))
                         (t *sht:ListTitle*))
        sht:lcnt   (if (= (cdr (assoc "@LISTCNT" sdat)) "0") "0" "1")
        sht:lauto  (if (= (cdr (assoc "@LISTAUTO" sdat)) "0") "0" "1")
        ret        (sht:list-dialog))
  (cond
    ((= ret 1)
     (sht:list-save)
     (vla-StartUndoMark doc)
     (setq r (sht:list-update sht:ltitle T))
     (vla-EndUndoMark doc)
     (sht:list-msg r T))
    ((= ret 2)
     (sht:list-save)
     (if (= (getvar "TILEMODE") 0)
       (progn
         (setvar "TILEMODE" 1)
         (princ "\nВедомость вставляется в модель (там листы SHEETS) - включена вкладка «Модель».")))
     (if (setq pt (getpoint "\nЛевый верхний угол ведомости листов - верх заголовка (к рамке листа; Enter - отмена): "))
       (progn
         (setq pt  (trans pt 1 0)
               hit (sht:sheet-at pt)
               sc  (if hit (cadr hit) (sht:list-ask-scale)))
         (vla-StartUndoMark doc)
         ;; s0.6.2: точка — верх заголовка (как у ведомости спецификаций)
         (setq tbl (vl-catch-all-apply 'sht:tbl-new (list pt sc sht:ltitle "LIST")))
         (if (vl-catch-all-error-p tbl)
           (princ (strcat "\nSHEETS: таблица не создана: " (vl-catch-all-error-message tbl)))
           (progn
             (setq r (sht:list-update sht:ltitle T)
                   h (+ *sht:ListTitleH* *sht:ListHeadH* (* *sht:ListRowH* (max 1 (nth 2 r)))))
             (princ (strcat "\nВедомость вставлена, 1:" (sht:n2s sc)
                            (if hit (strcat " (как у листа " (sht:sheet-no (car hit)) ")") "")
                            "; 185 x " (sht:n2s h) " мм листа вместе с заголовком (без переносов строк)."))
             (sht:list-msg r T)))
         (vla-EndUndoMark doc))
       (princ "\nВедомость не вставлена."))))
  (setq *sht:WatchTbl* (sht:table-count))           ; своя таблица — не повод обновлять (s0.6)
  (princ))

;;; --------------------------------------------------------------------------
;;;  15. ВЕДОМОСТЬ СПЕЦИФИКАЦИЙ (s0.6): SHEET_SPEC
;;;  Сводная ведомость спецификаций — та же таблица, что ведомость листов (15 / 140 / 30, шапка
;;;  «Лист / Наименование / Примечание», заголовок над рамкой), метка XData SHT_TABLE "SPEC".
;;;  Спецификации (решения Артёма, s0.6) — только таблицы AutoCAD, в заголовке (строка 0) которых есть
;;;  слово «Спецификация» («Спецификации»; «Ведомость спецификаций», «Ведомость деталей» — нет);
;;;  таблицы SHEETS не в счёт. Лист — лист SHEETS в модели, на котором точка вставки таблицы (левый
;;;  верхний угол); на листе без номера, вне листов SHEETS, на листе бумаги — не входят (окно их
;;;  показывает). Каждая спецификация — своей строкой: «Лист» — номер листа, «Наименование» — заголовок
;;;  таблицы целиком (без форматирования), «Примечание» — пусто. Порядок — по номерам листов (как
;;;  ведомость листов), на одном листе — слева направо, затем сверху вниз.
;;;  Вставка — кликом: точка — левый верхний угол всей таблицы, верх строки заголовка (привязать
;;;  к рамке листа или к низу ведомости листов). Обновление — вместе с ведомостью листов
;;;  (sht:list-update): при сохранении и печати, после команд SHEETS, SHEET_UPDATE; а также в конце
;;;  команды, после которой таблиц в чертеже стало больше / меньше (sht:watch-check), и s0.6.1 — в конце
;;;  команды, во время которой таблица изменилась (заголовок поправили, перенесли: sht:tbl-watch).
;;;  Правка в палитре «Свойства» (без команды) — в конце следующей команды или при сохранении.
;;; --------------------------------------------------------------------------

(setq *sht:SpecTitle* "Ведомость спецификаций")

;; Текст ячейки без форматирования MText: { } и коды \f \F \H \W \Q \T \A \C \c \p …; — убраны,
;; \P и \~ — пробел, \S…; (дробь) — «a/b», \L \l \O \o \K \k \N — убраны; прочие «\…» (\U+…, \\, \{) —
;; как есть (так они и запишутся в ведомость). Табуляция — пробел, пробелы подряд — один.
(defun sht:mt-plain (s / i n c d k r)
  (setq s (if (= (type s) 'STR) s "")
        i 1
        n (strlen s)
        r "")
  (while (<= i n)
    (setq c (substr s i 1))
    (cond
      ((and (= c "\\") (< i n))
       (setq d (substr s (1+ i) 1))
       (cond
         ((member d '("P" "~"))
          (setq r (strcat r " ")
                i (+ i 2)))
         ((member d '("L" "l" "O" "o" "K" "k" "N"))
          (setq i (+ i 2)))
         ((and (member d '("f" "F" "H" "W" "Q" "T" "A" "C" "c" "p" "S"))
               (setq k (vl-string-search ";" s (1+ i))))
          (if (= d "S")
            (setq r (strcat r (vl-string-translate "^#" "//" (substr s (+ i 2) (- k i 1))))))
          (setq i (+ k 2)))
         (t
          (setq r (strcat r c d)
                i (+ i 2)))))
      ((member c '("{" "}"))
       (setq i (1+ i)))
      (t
       (setq r (strcat r (if (= c "\t") " " c))
             i (1+ i)))))
  (while (setq k (vl-string-search "  " r))
    (setq r (strcat (substr r 1 k) (substr r (+ k 2)))))
  (sht:trim r))

;; В заголовке есть слово «Спецификация» / «Спецификации» (любыми буквами; «спецификаций» — нет)
(defun sht:spec-p (s)
  (and (= (type s) 'STR)
       (wcmatch s "*[Сс][Пп][Ее][Цц][Ии][Фф][Ии][Кк][Аа][Цц][Ии][ЯяИи]*")))

;; Заголовок таблицы: первая непустая ячейка строки 0, без форматирования
(defun sht:tbl-title (tbl / nc c s)
  (setq nc (sht:tbl-get tbl 'Columns)
        c  0
        s  "")
  (while (and (= s "") (numberp nc) (< c nc))
    (setq s (sht:mt-plain (sht:tbl-text tbl 0 c))
          c (1+ c)))
  s)

;; Лист из списка shs (ename номер точка масштаб ширина высота), на котором точка p, или nil
(defun sht:sheet-hit (shs p / res)
  (foreach q shs
    (if (and (not res)
             (<= (car (nth 2 q)) (car p) (+ (car (nth 2 q)) (* (nth 3 q) (nth 4 q))))
             (<= (cadr (nth 2 q)) (cadr p) (+ (cadr (nth 2 q)) (* (nth 3 q) (nth 5 q)))))
      (setq res q)))
  res)

;; Порядок спецификаций: по листам (sht:item<), на одном листе — слева направо, затем сверху вниз
(defun sht:spec< (a b)
  (cond
    ((sht:item< a b) T)
    ((sht:item< b a) nil)
    ((< (car (nth 5 a)) (- (car (nth 5 b)) 1e-6)) T)
    ((> (car (nth 5 a)) (+ (car (nth 5 b)) 1e-6)) nil)
    (t (> (cadr (nth 5 a)) (cadr (nth 5 b))))))

;; Спецификации: (на-листах-с-номером-по-порядку остальные). Спецификация — (ename-таблицы номер-листа
;; заголовок примечание ename-листа точка-таблицы точка-листа); у остальных вместо примечания — почему
;; не войдут. Номер и точка листа — на тех же местах, что у листов ведомости (sht:item<).
(defun sht:spec-items ( / shs inf wh ss i en ed tit p ms hit on off)
  (foreach q (sht:sheets)
    (setq inf (sht:sheet-info q)
          wh  (sht:fmt-wh (car inf) (cadr inf))
          shs (cons (list q (sht:trim (cdr (assoc "SHEET" (sht:attrs q)))) (nth 4 inf) (cadddr inf)
                          (car wh) (cadr wh) (caddr inf))
                    shs)))
  (setq shs (reverse shs))
  (if (setq ss (ssget "_X" '((0 . "ACAD_TABLE"))))
    (progn
      (setq i 0)
      (while (< i (sslength ss))
        (setq en (ssname ss i)
              ed (entget en)
              i  (1+ i))
        (if (and (not (sht:tbl-mark en))
                 (sht:spec-p (setq tit (sht:tbl-title (vlax-ename->vla-object en)))))
          (progn
            (setq p   (cdr (assoc 10 ed))
                  ms  (= (strcase (cond ((cdr (assoc 410 ed))) ("Model"))) "MODEL")
                  hit (if ms (sht:sheet-hit shs p)))
            (cond
              ((not ms)
               (setq off (cons (list en "" tit "на листе бумаги" nil p nil) off)))
              ((not hit)
               (setq off (cons (list en "" tit "не на листе SHEETS" nil p nil) off)))
              ((/= (sht:fbase (nth 6 hit)) "3")                  ; s0.10: не основной комплект
               (setq off (cons (list en "" tit (strcat "на листе формы " (sht:fbase (nth 6 hit))
                                                       " (не в ведомости листов)")
                                     (car hit) p (nth 2 hit))
                               off)))
              ((= (nth 1 hit) "")
               (setq off (cons (list en "" tit "на листе без номера" (car hit) p (nth 2 hit)) off)))
              (t
               (setq on (cons (list en (nth 1 hit) tit "" (car hit) p (nth 2 hit)) on)))))))))
  (list (vl-sort on 'sht:spec<) (reverse off)))

;; Обновить таблицы ведомости спецификаций. title — заголовок (nil — не трогать), force — оформление
;; заново. Таблиц нет — nil (спецификации и не ищутся); иначе (таблиц-изменено таблиц-всего спецификаций).
(defun sht:spec-update (title force / tbls items nt)
  (if (setq tbls (sht:kind-tables "SPEC"))
    (progn
      (setq items (car (sht:spec-items))
            nt    0)
      (foreach tbl tbls
        (if (sht:tbl-fill tbl items title force) (setq nt (1+ nt))))
      (list nt (length tbls) (length items)))))

;; Сообщение об обновлении; all — и когда таблицы не менялись
(defun sht:spec-msg (r all)
  (if (or all (> (car r) 0))
    (princ (strcat "\nВедомость спецификаций: спецификаций " (itoa (nth 2 r))
                   (cond ((= (cadr r) 0) " - таблицы ведомости спецификаций в чертеже нет (вставить: SHEET_SPEC)")
                         ((> (car r) 0) (strcat ", обновлено таблиц: " (itoa (car r)) " из " (itoa (cadr r))))
                         (t ", таблица без изменений"))
                   "."))))

;; --- окно «Ведомость спецификаций» -----------------------------------------------
;; Переменные окна (локальные в c:SHEET_SPEC): sht:sitems sht:soff — спецификации на листах с номером /
;; остальные, sht:stbls — таблицы ведомости спецификаций, sht:stitle — заголовок, sht:lauto — "1" / "0"
;; (автообновление — общее с ведомостью листов).

(defun sht:spec-info ()
  (strcat "Спецификаций в ведомости: " (itoa (length sht:sitems)) ". "
          (if sht:stbls
            (strcat "Таблиц ведомости спецификаций в чертеже: " (itoa (length sht:stbls))
                    " - «Обновить» перепишет их.")
            "Таблицы ведомости спецификаций в чертеже нет - «Вставить ведомость <».")))

(defun sht:spec-init ()
  (start_list "sht_SList")
  (foreach it sht:sitems (add_list (sht:list-line it)))
  (end_list)
  (start_list "sht_SOff")
  (foreach it sht:soff (add_list (strcat "-\t" (nth 2 it) "\t" (nth 3 it))))
  (end_list)
  (set_tile "sht_SInfo" (sht:spec-info))
  (set_tile "sht_STitle" sht:stitle)
  (set_tile "sht_SAuto" sht:lauto)
  (action_tile "sht_SIns" "(sht:spec-ok 2)")
  (action_tile "accept" "(sht:spec-ok 1)"))

;; «Обновить» (1) / «Вставить ведомость <» (2)
(defun sht:spec-ok (code)
  (setq sht:stitle (sht:trim (get_tile "sht_STitle"))
        sht:lauto  (get_tile "sht_SAuto"))
  (if (= sht:stitle "")
    (set_tile "error" "Впишите заголовок ведомости.")
    (done_dialog code)))

(defun sht:spec-dialog ( / dcl_id dclFile ret)
  (setq ret 0)
  (if (sht:dlg-load)
    (if (new_dialog "sht_spec" dcl_id)
      (progn
        (sht:spec-init)
        (setq ret (start_dialog)))
      (princ "\nSHEETS: не удалось открыть окно.")))
  (sht:dlg-cleanup)
  ret)

;; Настройки — в словарь чертежа (если поменялись)
(defun sht:spec-save ( / sdat new)
  (setq sdat (sht:set-read)
        new  (sht:alist-put (sht:alist-put sdat "@SPECTITLE" sht:stitle) "@LISTAUTO" sht:lauto))
  (if (not (equal new sdat)) (sht:set-write new)))

(defun c:SHEET_SPEC ( / doc sdat d ret pt hit sc tbl r h
                        sht:sitems sht:soff sht:stbls sht:stitle sht:lauto sht:litems)
  (setq doc  (sht:doc)
        sdat (sht:prepare))
  (sht:dblclick-setup)
  (sht:defaults)
  (setq d          (sht:spec-items)
        sht:sitems (car d)
        sht:soff   (cadr d)
        sht:stbls  (sht:kind-tables "SPEC")
        sht:stitle (cond ((and sht:stbls (/= (sht:tbl-text (car sht:stbls) 0 0) ""))
                          (sht:tbl-text (car sht:stbls) 0 0))
                         ((/= (sht:trim (cdr (assoc "@SPECTITLE" sdat))) "")
                          (cdr (assoc "@SPECTITLE" sdat)))
                         (t *sht:SpecTitle*))
        sht:lauto  (if (= (cdr (assoc "@LISTAUTO" sdat)) "0") "0" "1")
        ret        (sht:spec-dialog))
  (cond
    ((= ret 1)
     (sht:spec-save)
     (vla-StartUndoMark doc)
     (setq r (sht:spec-update sht:stitle T))
     (vla-EndUndoMark doc)
     (sht:spec-msg (cond (r) ((list 0 0 (length sht:sitems)))) T))
    ((= ret 2)
     (sht:spec-save)
     (if (= (getvar "TILEMODE") 0)
       (progn
         (setvar "TILEMODE" 1)
         (princ "\nВедомость вставляется в модель (там листы SHEETS) - включена вкладка «Модель».")))
     (if (setq pt (getpoint (strcat "\nЛевый верхний угол ведомости спецификаций - верх заголовка "
                                    "(к рамке листа или к низу ведомости листов; Enter - отмена): ")))
       (progn
         (setq pt         (trans pt 1 0)
               hit        (sht:sheet-at pt)
               sht:litems (car (sht:list-items))         ; масштаб по умолчанию — как у первого листа
               sc         (if hit (cadr hit) (sht:list-ask-scale)))
         (vla-StartUndoMark doc)
         (setq tbl (vl-catch-all-apply 'sht:tbl-new (list pt sc sht:stitle "SPEC")))
         (if (vl-catch-all-error-p tbl)
           (princ (strcat "\nSHEETS: таблица не создана: " (vl-catch-all-error-message tbl)))
           (progn
             (setq r (cond ((sht:spec-update sht:stitle T)) ((list 0 0 (length sht:sitems))))
                   h (+ *sht:ListTitleH* *sht:ListHeadH* (* *sht:ListRowH* (max 1 (nth 2 r)))))
             (princ (strcat "\nВедомость спецификаций вставлена, 1:" (sht:n2s sc)
                            (if hit (strcat " (как у листа " (sht:sheet-no (car hit)) ")") "")
                            "; 185 x " (sht:n2s h) " мм листа вместе с заголовком (без переносов строк)."))
             (sht:spec-msg r T)))
         (vla-EndUndoMark doc))
       (princ "\nВедомость спецификаций не вставлена."))))
  (setq *sht:WatchTbl* (sht:table-count))
  (princ))


;;; --------------------------------------------------------------------------
;;;  15а. ВЕДОМОСТЬ ССЫЛОЧНЫХ И ПРИЛАГАЕМЫХ ДОКУМЕНТОВ (s0.10): SHEET_REFS
;;;  Образец Артёма («Форматы.dxf»): столбцы «Обозначение / Наименование / Примечание» 60 / 95 / 30,
;;;  шапка 15, строки 8, заголовок 3,5 над таблицей — как у прочих ведомостей (таблица AutoCAD, метка
;;;  XData SHT_TABLE "REFS"); ставится на лист общих данных кликом — точка — верх заголовка.
;;;  Разделы — подчёркнутый заголовок по центру столбца «Наименование»:
;;;  «Ссылочные документы» — вписываются вручную в окне SHEET_REFS (словарь чертежа: @REF1, @REF2 …
;;;  = «обозначение|наименование|примечание»); записей нет — раздела нет;
;;;  «Прилагаемые документы» — из листов формы 4 (решение Артёма): листы с одинаковой графой 1 — один
;;;  документ, одна строка: «Обозначение» — графа 1, «Наименование» — графа 5 (клетка 70 x 25) первого
;;;  листа, «Примечание» — пусто. Данные форм 5 и 6 ни в какие таблицы не идут.
;;;  Обновление — вместе с ведомостью листов (sht:list-update): при сохранении и печати, после команд
;;;  SHEETS, SHEET_UPDATE.
;;; --------------------------------------------------------------------------

(setq *sht:RefTitle*  "Ведомость ссылочных и прилагаемых документов"
      *sht:RefHead*   '("Обозначение" "Наименование" "Примечание")
      *sht:RefCols*   '(60.0 95.0 30.0)
      *sht:RefSecRef* "\\LСсылочные документы\\l"
      *sht:RefSecAtt* "\\LПрилагаемые документы\\l")

;; Ссылочные документы из данных чертежа: ((обозначение наименование примечание) …)
(defun sht:refs-load (sdat / i v l res)
  (setq i 1)
  (while (setq v (cdr (assoc (strcat "@REF" (itoa i)) sdat)))
    (setq l   (sht:split v "|")
          res (cons (list (car l) (cond ((cadr l)) ("")) (cond ((caddr l)) (""))) res)
          i   (1+ i)))
  (reverse res))

;; Данные чертежа sdat со ссылочными документами refs вместо прежних @REF1, @REF2 …
(defun sht:refs-put (sdat refs / res i)
  (foreach p sdat
    (if (not (and (> (strlen (car p)) 4) (= (substr (car p) 1 4) "@REF") (wcmatch (substr (car p) 5 1) "#")))
      (setq res (cons p res))))
  (setq res (reverse res)
        i   1)
  (foreach r refs
    (setq res (append res (list (cons (strcat "@REF" (itoa i)) (strcat (car r) "|" (cadr r) "|" (caddr r)))))
          i   (1+ i)))
  res)

;; Документы раздела «Прилагаемые документы»: документы (sht:doc-items), в которых есть лист формы 4
(defun sht:refs-docs ()
  (vl-remove-if-not '(lambda (d) (vl-some '(lambda (it) (= (sht:fbase (nth 4 it)) "4")) (cadr d)))
                    (sht:doc-items)))

;; Строки таблицы под шапкой: разделы с заголовками; строка — (nil обозначение наименование примечание),
;; как у листов ведомости (sht:list-cells)
(defun sht:refs-rows (refs docs / res)
  (if refs
    (setq res (cons (list nil "" *sht:RefSecRef* "")
                    (mapcar '(lambda (r) (list nil (car r) (cadr r) (caddr r))) refs))))
  (if docs
    (setq res (append res (list (list nil "" *sht:RefSecAtt* ""))
                      (mapcar '(lambda (d) (list nil (car d) (sht:doc-name d) "")) docs))))
  res)

;; Обновить таблицы ведомости ссылочных документов. title — заголовок (nil — не трогать), force —
;; оформление заново. Таблиц нет — nil; иначе (таблиц-изменено таблиц-всего прилагаемых ссылочных).
(defun sht:refs-update (title force / tbls refs docs rows nt)
  (if (setq tbls (sht:kind-tables "REFS"))
    (progn
      (setq refs (sht:refs-load (sht:set-read))
            docs (sht:refs-docs)
            rows (sht:refs-rows refs docs)
            nt   0)
      (foreach tbl tbls
        (if (sht:tbl-fill tbl rows title force) (setq nt (1+ nt))))
      (list nt (length tbls) (length docs) (length refs)))))

;; Сообщение об обновлении; all — и когда таблицы не менялись
(defun sht:refs-msg (r all)
  (if (or all (> (car r) 0))
    (princ (strcat "\nВедомость ссылочных и прилагаемых документов: прилагаемых " (itoa (nth 2 r))
                   ", ссылочных " (itoa (nth 3 r))
                   (cond ((= (cadr r) 0) " - таблицы в чертеже нет (вставить: SHEET_REFS)")
                         ((> (car r) 0) (strcat ", обновлено таблиц: " (itoa (car r)) " из " (itoa (cadr r))))
                         (t ", таблица без изменений"))
                   "."))))

;; --- окно «Ведомость ссылочных и прилагаемых документов» -----------------------------
;; Переменные окна (локальные в c:SHEET_REFS): sht:ratt — прилагаемые документы (sht:refs-docs),
;; sht:rref — ссылочные ((обозначение наименование примечание) …), sht:rsel — выбранная строка
;; ссылочных (номер с 0 или nil), sht:rtbls — таблицы, sht:rtitle — заголовок, sht:lauto — "1" / "0"
;; (автообновление — общее для всех ведомостей).

;; Список lst, в котором элемент номер i заменён на v (v = nil — убран)
(defun sht:nth-set (lst i v / k res)
  (setq k 0)
  (foreach x lst
    (cond ((/= k i) (setq res (cons x res)))
          (v (setq res (cons v res))))
    (setq k (1+ k)))
  (reverse res))

;; Поменять местами элементы i и i+1
(defun sht:nth-swap (lst i / a b)
  (setq a (nth i lst)
        b (nth (1+ i) lst))
  (sht:nth-set (sht:nth-set lst i b) (1+ i) a))

(defun sht:refs-info ()
  (strcat "Прилагаемых документов: " (itoa (length sht:ratt)) ", ссылочных: " (itoa (length sht:rref)) ". "
          (if sht:rtbls
            (strcat "Таблиц ведомости в чертеже: " (itoa (length sht:rtbls)) " - «Обновить» перепишет их.")
            "Таблицы ведомости в чертеже нет - «Вставить ведомость <».")))

;; Список ссылочных документов в окне
(defun sht:refs-fill ()
  (start_list "sht_RRef")
  (foreach r sht:rref (add_list (strcat (car r) "\t" (cadr r) "\t" (caddr r))))
  (end_list)
  (if (and sht:rsel (< sht:rsel (length sht:rref)))
    (set_tile "sht_RRef" (itoa sht:rsel)))
  (set_tile "sht_RInfo" (sht:refs-info)))

(defun sht:refs-init ()
  (start_list "sht_RAtt")
  (foreach d sht:ratt
    (add_list (strcat (car d) "\t" (sht:doc-name d) "\t" (itoa (length (cadr d))) " л.")))
  (end_list)
  (sht:refs-fill)
  (set_tile "sht_RTitle" sht:rtitle)
  (set_tile "sht_RAuto" sht:lauto)
  (action_tile "sht_RRef" "(sht:refs-pick)")
  (action_tile "sht_RAdd" "(sht:refs-edit 1)")
  (action_tile "sht_RChg" "(sht:refs-edit 2)")
  (action_tile "sht_RDel" "(sht:refs-edit 3)")
  (action_tile "sht_RUp" "(sht:refs-edit 4)")
  (action_tile "sht_RDn" "(sht:refs-edit 5)")
  (action_tile "sht_RIns" "(sht:refs-ok 2)")
  (action_tile "accept" "(sht:refs-ok 1)"))

;; Щелчок по строке ссылочных — в поля для правки
(defun sht:refs-pick ( / r)
  (setq sht:rsel (atoi (get_tile "sht_RRef"))
        r        (nth sht:rsel sht:rref))
  (if r
    (progn
      (set_tile "sht_RObo" (car r))
      (set_tile "sht_RNam" (cadr r))
      (set_tile "sht_RNote" (caddr r)))))

;; Кнопки: 1 — добавить, 2 — заменить выбранную строку, 3 — удалить, 4 — выше, 5 — ниже.
;; «|» в тексте — «/» (разделитель записи в данных чертежа).
(defun sht:refs-edit (op / r n)
  (setq r (mapcar '(lambda (k) (sht:trim (vl-string-translate "|" "/" (get_tile k))))
                  '("sht_RObo" "sht_RNam" "sht_RNote"))
        n (length sht:rref))
  (set_tile "error" "")
  (cond
    ((= op 1)
     (if (and (= (car r) "") (= (cadr r) ""))
       (set_tile "error" "Впишите обозначение или наименование документа.")
       (setq sht:rref (append sht:rref (list r))
             sht:rsel n)))
    ((not (and sht:rsel (< sht:rsel n)))
     (set_tile "error" "Выберите строку в списке ссылочных документов."))
    ((= op 2) (setq sht:rref (sht:nth-set sht:rref sht:rsel r)))
    ((= op 3) (setq sht:rref (sht:nth-set sht:rref sht:rsel nil)
                    sht:rsel nil))
    ((and (= op 4) (> sht:rsel 0))
     (setq sht:rref (sht:nth-swap sht:rref (1- sht:rsel))
           sht:rsel (1- sht:rsel)))
    ((and (= op 5) (< sht:rsel (1- n)))
     (setq sht:rref (sht:nth-swap sht:rref sht:rsel)
           sht:rsel (1+ sht:rsel))))
  (sht:refs-fill))

;; «Обновить» (1) / «Вставить ведомость <» (2)
(defun sht:refs-ok (code)
  (setq sht:rtitle (sht:trim (get_tile "sht_RTitle"))
        sht:lauto  (get_tile "sht_RAuto"))
  (if (= sht:rtitle "")
    (set_tile "error" "Впишите заголовок ведомости.")
    (done_dialog code)))

(defun sht:refs-dialog ( / dcl_id dclFile ret)
  (setq ret 0)
  (if (sht:dlg-load)
    (if (new_dialog "sht_refs" dcl_id)
      (progn
        (sht:refs-init)
        (setq ret (start_dialog)))
      (princ "\nSHEETS: не удалось открыть окно.")))
  (sht:dlg-cleanup)
  ret)

;; Ссылочные, заголовок, автообновление — в данные чертежа (если поменялись)
(defun sht:refs-save ( / sdat new)
  (setq sdat (sht:set-read)
        new  (sht:alist-put (sht:alist-put (sht:refs-put sdat sht:rref) "@REFTITLE" sht:rtitle)
                            "@LISTAUTO" sht:lauto))
  (if (not (equal new sdat)) (sht:set-write new)))

(defun c:SHEET_REFS ( / doc sdat ret pt hit sc tbl r h
                        sht:ratt sht:rref sht:rsel sht:rtbls sht:rtitle sht:lauto sht:litems)
  (setq doc  (sht:doc)
        sdat (sht:prepare))
  (sht:dblclick-setup)
  (sht:defaults)
  (setq sht:ratt   (sht:refs-docs)
        sht:rref   (sht:refs-load sdat)
        sht:rtbls  (sht:kind-tables "REFS")
        sht:rtitle (cond ((and sht:rtbls (/= (sht:tbl-text (car sht:rtbls) 0 0) ""))
                          (sht:tbl-text (car sht:rtbls) 0 0))
                         ((/= (sht:trim (cdr (assoc "@REFTITLE" sdat))) "")
                          (cdr (assoc "@REFTITLE" sdat)))
                         (t *sht:RefTitle*))
        sht:lauto  (if (= (cdr (assoc "@LISTAUTO" sdat)) "0") "0" "1")
        ret        (sht:refs-dialog))
  (cond
    ((= ret 1)
     (sht:refs-save)
     (vla-StartUndoMark doc)
     (setq r (sht:refs-update sht:rtitle T))
     (vla-EndUndoMark doc)
     (sht:refs-msg (cond (r) ((list 0 0 (length sht:ratt) (length sht:rref)))) T))
    ((= ret 2)
     (sht:refs-save)
     (if (= (getvar "TILEMODE") 0)
       (progn
         (setvar "TILEMODE" 1)
         (princ "\nВедомость вставляется в модель (там листы SHEETS) - включена вкладка «Модель».")))
     (if (setq pt (getpoint (strcat "\nЛевый верхний угол ведомости ссылочных и прилагаемых документов - "
                                    "верх заголовка (Enter - отмена): ")))
       (progn
         (setq pt         (trans pt 1 0)
               hit        (sht:sheet-at pt)
               sht:litems (car (sht:list-items))         ; масштаб по умолчанию — как у первого листа
               sc         (if hit (cadr hit) (sht:list-ask-scale)))
         (vla-StartUndoMark doc)
         (setq tbl (vl-catch-all-apply 'sht:tbl-new (list pt sc sht:rtitle "REFS")))
         (if (vl-catch-all-error-p tbl)
           (princ (strcat "\nSHEETS: таблица не создана: " (vl-catch-all-error-message tbl)))
           (progn
             (setq r (cond ((sht:refs-update sht:rtitle T)) ((list 0 0 (length sht:ratt) (length sht:rref))))
                   h (+ *sht:ListTitleH* *sht:ListHeadH*
                        (* *sht:ListRowH* (max 1 (length (sht:refs-rows sht:rref sht:ratt))))))
             (princ (strcat "\nВедомость ссылочных и прилагаемых документов вставлена, 1:" (sht:n2s sc)
                            (if hit (strcat " (как у листа " (sht:sheet-no (car hit)) ")") "")
                            "; 185 x " (sht:n2s h) " мм листа вместе с заголовком (без переносов строк)."))
             (sht:refs-msg r T)))
         (vla-EndUndoMark doc))
       (princ "\nВедомость ссылочных и прилагаемых документов не вставлена."))))
  (setq *sht:WatchTbl* (sht:table-count))
  (princ))

;;; --------------------------------------------------------------------------
;;;  16. ПОДПИСИ И ЛОГОТИП (s0.7 — шаг плана s0.4): SHEET_SIGN
;;;  Подпись — блок AutoCAD в графе «Подп.» напротив фамилии (графа 11, строки 1-6 основной надписи,
;;;  форма 3). Какой блок у какой фамилии — задаётся один раз на комплект (окно SHEET_SIGN; словарь
;;;  чертежа: @SIGN:<фамилия> = имя блока, "" — без подписи) и расходится по всем листам: подпись
;;;  стоит везде, где в штампе эта фамилия. Логотип — блок или картинка (IMAGE) в графе 9 на всех
;;;  листах формы 3 (@LOGO = "B:<блок>" / "I:<файл>"; "" — нет). Короткий штамп (форма 6) — без них.
;;;  Размер: подпись — вписать в графу 15 x 5 с зазором 0,5 (@SIGNFIT "1") или как нарисована —
;;;  1 ед. блока = 1 мм листа ("0"); логотип-блок — вписать в графу 50 x 15 с зазором 1 (@LOGOFIT)
;;;  или как нарисован; картинка — всегда вписать. Середина габарита — в середине графы.
;;;  Подписи и логотип — отдельные объекты в модели: подписи — слой 0000_Подписи (заморозить —
;;;  печать без подписей; программа слой только создаёт, вкл./выкл. не трогает), логотип — слой
;;;  листа 0000_Формат. Метка XData SHT_SIGN: вид ("SIGN" / "LOGO"), handle листа, строка, точка
;;;  вставки в мм листа (x y), масштаб (у картинки — ширина, мм листа), источник ("B:…" / "I:…").
;;;  Сверка (sht:sign-sync): объект у своего листа, на своём месте, того же источника — остаётся;
;;;  иначе (лист сдвинули без подписей, удалили, скопировали; фамилию поменяли; блок сменили) —
;;;  удаляется, недостающие ставятся заново. Подписи всегда соответствуют фамилиям в штампах.
;;;  Когда: SHEET_SIGN «Расставить» и SHEET_UPDATE — всё заново (габариты блоков меряются заново);
;;;  в конце SHEET_NEW, окна «Лист», SHEET_DATA, SHEET_APPLY, перед печатью SHEET_PLOT, перед
;;;  сохранением (реактор команд) и в конце команды, после которой листов стало больше / меньше
;;;  или лист сдвинули / фамилию в нём поменяли (реактор *sht:RSign* — только если подписи или
;;;  логотип заданы; сам реактор только ставит флаг). После U / UNDO — при сохранении.
;;; --------------------------------------------------------------------------

(setq *sht:LaySign*  "0000_Подписи"
      *sht:SignApp*  "SHT_SIGN"
      *sht:SignGap*  0.5                  ; зазор вписывания подписи, мм листа (с каждой стороны)
      *sht:LogoGap*  1.0                  ; зазор вписывания логотипа
      *sht:NameTags* '("NAME1" "NAME2" "NAME3" "NAME4" "NAME5" "NAME6")
      *sht:ImgExt*   "png;jpg;jpeg;bmp;tif;tiff;gif")

;; Без повторов (без учёта регистра)
(defun sht:uniq-ci (lst / res)
  (foreach x lst
    (if (not (vl-some '(lambda (y) (= (sht:lc y) (sht:lc x))) res)) (setq res (append res (list x)))))
  res)

;; Строчные буквы (латиница и кириллица; strcase для кириллицы не надёжен)
(defun sht:lc (s)
  (vl-string-translate "ABCDEFGHIJKLMNOPQRSTUVWXYZАБВГДЕЁЖЗИЙКЛМНОПРСТУФХЦЧШЩЪЫЬЭЮЯ"
                       "abcdefghijklmnopqrstuvwxyzабвгдеёжзийклмнопрстуфхцчшщъыьэюя" s))

;; Настройки из словаря чертежа: (фамилии вписать-подпись логотип вписать-логотип);
;; фамилии — (("Иванов" . "Подпись_Иванов") …), "" — без подписи
(defun sht:sign-cfg (sdat / res)
  (foreach p sdat
    (if (and (> (strlen (car p)) 6) (= (substr (car p) 1 6) "@SIGN:"))
      (setq res (cons (cons (substr (car p) 7) (cdr p)) res))))
  (list (reverse res)
        (if (= (cdr (assoc "@SIGNFIT" sdat)) "0") "0" "1")
        (cond ((cdr (assoc "@LOGO" sdat))) (""))
        (if (= (cdr (assoc "@LOGOFIT" sdat)) "0") "0" "1")))

;; Подписи или логотип заданы?
(defun sht:sign-on-p (cfg)
  (or (vl-some '(lambda (p) (/= (cdr p) "")) (car cfg))
      (/= (caddr cfg) "")))

;; Имя блока, как оно в чертеже (без учёта регистра), или nil; на время сверки — запоминается
(defun sht:blk-real (b / c r)
  (if (setq c (assoc b *sht:BlkReal*))
    (cdr c)
    (progn
      (setq r (tblsearch "BLOCK" b)
            r (if r (cdr (assoc 2 r))))
      (setq *sht:BlkReal* (cons (cons b r) *sht:BlkReal*))
      r)))

;; Нет блока b — запомнить для сообщения
(defun sht:sign-miss (b)
  (if (not (member b *sht:SignMiss*)) (setq *sht:SignMiss* (append *sht:SignMiss* (list b))))
  nil)

;; Строки подписей формы (s0.10): (число верх) — формы 3, 4: 6 строк, верх y 30; форма 5: 5 строк,
;; верх y 25 (мм от угла рамки поля); короткий штамп (форма 6) — nil (подписей и логотипа нет)
(defun sht:sign-rows (form / b)
  (setq b (sht:fbase form))
  (cond ((member b '("3" "4")) (list 6 30.0))
        ((= b "5") (list 5 25.0))))

;; Что должно стоять на листе (формы 3, 4, 5): ((вид строка источник cx cy ширина высота вписать) …):
;; источник — "B:<блок>" / "I:<файл>"; cx cy — середина графы, мм листа от левого нижнего угла листа.
(defun sht:sign-want (inf a cfg / br i nm b bb res lg sr)
  (if (setq sr (sht:sign-rows (caddr inf)))
    (progn
      (setq br (sht:anchor "BR" (sht:fmt-wh (car inf) (cadr inf)))
            i  1)
      ;; подписи: графа «Подп.» x -145…-130, строка i — y (верх - 5i)…(верх + 5 - 5i) от угла рамки поля
      (repeat (car sr)
        (setq nm (sht:trim (cdr (assoc (strcat "NAME" (itoa i)) a))))
        (if (and (/= nm "")
                 (setq b (cdr (assoc nm (car cfg))))
                 (/= b ""))
          (if (setq bb (sht:blk-real b))
            (setq res (cons (list "SIGN" i (strcat "B:" bb) (- (car br) 137.5)
                                  (+ (cadr br) (- (+ (cadr sr) 2.5) (* 5.0 i)))
                                  15.0 5.0 (cadr cfg))
                            res))
            (sht:sign-miss b)))
        (setq i (1+ i)))
      ;; логотип: графа 9 x -50…0, y 0…15
      (setq lg (caddr cfg))
      (cond
        ((= lg ""))
        ((= (substr lg 1 2) "I:")
         (setq res (cons (list "LOGO" 0 lg (- (car br) 25.0) (+ (cadr br) 7.5) 50.0 15.0 "1") res)))
        ((setq b (sht:blk-real (substr lg 3)))
         (setq res (cons (list "LOGO" 0 (strcat "B:" b) (- (car br) 25.0) (+ (cadr br) 7.5) 50.0 15.0 (cadddr cfg))
                         res)))
        (t (sht:sign-miss (substr lg 3))))))
  (reverse res))

;; Точка листа (мм от левого нижнего угла, без поворота) -> мировая; ed — entget листа
(defun sht:sheet-pt (ed lx ly / p sc a)
  (setq p  (cdr (assoc 10 ed))
        sc (cond ((cdr (assoc 41 ed))) (1.0))
        a  (cond ((cdr (assoc 50 ed))) (0.0)))
  (list (+ (car p) (* sc (- (* lx (cos a)) (* ly (sin a)))))
        (+ (cadr p) (* sc (+ (* lx (sin a)) (* ly (cos a)))))
        (cond ((caddr p)) (0.0))))

(defun sht:ang-eq (a b / d)
  (setq d (rem (abs (- a b)) (* 2.0 pi)))
  (or (< d 1e-6) (< (- (* 2.0 pi) d) 1e-6)))

;; Подписи и логотипы в чертеже: ((ename вид handle-листа строка x y масштаб источник) …)
(defun sht:sign-objs ( / ss i en xd res)
  (if (setq ss (ssget "_X" (list (list -3 (list *sht:SignApp*)))))
    (progn
      (setq i 0)
      (while (< i (sslength ss))
        (setq en (ssname ss i)
              i  (1+ i)
              xd (mapcar 'cdr (cdr (assoc *sht:SignApp* (cdr (assoc -3 (entget en (list *sht:SignApp*))))))))
        (if (= (length xd) 7)
          (setq res (cons (cons en xd) res))))))
  (reverse res))

(defun sht:sign-xd-set (en kind h row lx ly k src)
  (regapp *sht:SignApp*)
  (entmod (append (entget en)
                  (list (list -3 (list *sht:SignApp* (cons 1000 kind) (cons 1000 h) (cons 1070 row)
                                       (cons 1040 (float lx)) (cons 1040 (float ly)) (cons 1040 (float k))
                                       (cons 1000 src)))))))

;; Объект o (из sht:sign-objs) стоит по своим данным у листа ed: точка, поворот, масштаб / ширина
(defun sht:sign-at-p (o ed / oe q sc a tol v r)
  (setq q   (sht:sheet-pt ed (nth 4 o) (nth 5 o))
        sc  (cond ((cdr (assoc 41 ed))) (1.0))
        a   (cond ((cdr (assoc 50 ed))) (0.0))
        tol (* 0.001 sc)
        oe  (entget (car o)))
  (cond
    ((null oe) nil)
    ((= (cdr (assoc 0 oe)) "INSERT")
     (and (< (distance (cdr (assoc 10 oe)) q) tol)
          (equal (cdr (assoc 41 oe)) (* (nth 6 o) sc) (* 1e-6 (abs (* (nth 6 o) sc))))
          (sht:ang-eq (cond ((cdr (assoc 50 oe))) (0.0)) a)
          (= (strcat "B:" (cdr (assoc 2 oe))) (nth 7 o))))
    ((= (cdr (assoc 0 oe)) "IMAGE")
     (setq v (vlax-ename->vla-object (car o))
           r (sht:tbl-get v 'Origin))
     (and r
          (< (distance r q) tol)
          (sht:ang-eq (cond ((sht:tbl-get v 'Rotation)) (0.0)) a)
          (equal (sht:tbl-get v 'ImageWidth) (* (nth 6 o) sc) tol)))))

;; Габарит блока при вставке 1:1 без поворота: (dx dy ширина высота) — середина габарита от
;; базовой точки; не измерился — nil. По объектам описания блока (без определений атрибутов):
;; чертёж не меняется, временных вставок нет.
(defun sht:blk-box (name / c blk o0 r mn mx x1 y1 x2 y2)
  (if (setq c (assoc name *sht:BoxCache*))
    (cdr c)
    (progn
      (setq blk (vl-catch-all-apply 'vla-Item (list (vla-get-Blocks (sht:doc)) name)))
      (if (not (vl-catch-all-error-p blk))
        (vlax-for o blk
          (if (/= (vla-get-ObjectName o) "AcDbAttributeDefinition")
            (progn
              (setq r (vl-catch-all-apply 'vla-GetBoundingBox (list o 'mn 'mx)))
              (if (not (vl-catch-all-error-p r))
                (setq mn (vlax-safearray->list mn)
                      mx (vlax-safearray->list mx)
                      x1 (if x1 (min x1 (car mn)) (car mn))
                      y1 (if y1 (min y1 (cadr mn)) (cadr mn))
                      x2 (if x2 (max x2 (car mx)) (car mx))
                      y2 (if y2 (max y2 (cadr mx)) (cadr mx))))))))
      ;; базовая точка блока (BASE) — в точку вставки: середина — от неё
      (setq o0 (if (vl-catch-all-error-p blk) nil (sht:tbl-get blk 'Origin))
            o0 (if (and (listp o0) (numberp (car o0))) o0 (list 0.0 0.0 0.0))
            r  (if x1 (list (- (/ (+ x1 x2) 2.0) (car o0)) (- (/ (+ y1 y2) 2.0) (cadr o0)) (- x2 x1) (- y2 y1))))
      (setq *sht:BoxCache* (cons (cons name r) *sht:BoxCache*))
      r)))

;; Масштаб вписывания габарита bw x bh в графу w x h с зазором g (плоский — по другой стороне)
(defun sht:fit-k (bw bh w h g)
  (setq w (- w g g)
        h (- h g g))
  (cond ((and (> bw 1e-9) (> bh 1e-9)) (min (/ w bw) (/ h bh)))
        ((> bw 1e-9) (/ w bw))
        ((> bh 1e-9) (/ h bh))
        (t 1.0)))

;; Поставить слот w на лист s (ename entget handle слоты): блок или картинка. Возвращает ename.
(defun sht:sign-put (s w)
  (if (= (substr (nth 2 w) 1 2) "I:")
    (sht:sign-put-img s w (substr (nth 2 w) 3))
    (sht:sign-put-blk s w (substr (nth 2 w) 3) (if (= (car w) "SIGN") *sht:LaySign* *sht:LayFmt*))))

(defun sht:sign-put-blk (s w name lay / ed bx k lx ly sc ins en)
  (setq ed (cadr s)
        bx (sht:blk-box name)
        k  (if (and bx (= (nth 7 w) "1"))
             (sht:fit-k (nth 2 bx) (nth 3 bx) (nth 5 w) (nth 6 w)
                        (if (= (car w) "LOGO") *sht:LogoGap* *sht:SignGap*))
             1.0)
        lx (- (nth 3 w) (* k (if bx (car bx) 0.0)))
        ly (- (nth 4 w) (* k (if bx (cadr bx) 0.0)))
        sc (cond ((cdr (assoc 41 ed))) (1.0))
        ins (vla-InsertBlock (sht:ms) (vlax-3d-point (sht:sheet-pt ed lx ly)) name
                             (* k sc) (* k sc) (* k sc) (cond ((cdr (assoc 50 ed))) (0.0))))
  (vla-put-Layer ins lay)
  (setq en (vlax-vla-object->ename ins))
  (sht:sign-xd-set en (car w) (caddr s) (cadr w) lx ly k (strcat "B:" (cdr (assoc 2 (entget en)))))
  en)

;; Картинка-логотип: вписать в графу по сторонам картинки (вставка 1:1 -> ширина и высота -> масштаб)
(defun sht:sign-put-img (s w path / ed sc img iw ih kw hw lx ly en)
  (setq ed  (cadr s)
        sc  (cond ((cdr (assoc 41 ed))) (1.0))
        img (vlax-invoke (sht:ms) 'AddRaster path (sht:sheet-pt ed (nth 3 w) (nth 4 w)) 1.0 0.0)
        en  (vlax-vla-object->ename img)
        iw  (sht:tbl-get img 'ImageWidth)
        ih  (sht:tbl-get img 'ImageHeight))
  (if (not (and (numberp iw) (numberp ih) (> iw 0) (> ih 0)))
    (progn
      (entdel en)
      (setq en nil)
      (princ (strcat "\nSHEETS: у картинки не определился размер: " path)))
    (progn
      (setq kw (min (- (nth 5 w) (* 2.0 *sht:LogoGap*)) (* (- (nth 6 w) (* 2.0 *sht:LogoGap*)) (/ (float iw) ih)))
            hw (* kw (/ (float ih) iw))
            lx (- (nth 3 w) (/ kw 2.0))
            ly (- (nth 4 w) (/ hw 2.0)))
      (sht:tbl-put img 'ScaleFactor (/ (* kw sc) iw))
      (if (not (equal (sht:tbl-get img 'ImageWidth) (* kw sc) (* 1e-6 kw sc)))
        (progn
          (sht:tbl-put img 'ImageWidth (* kw sc))
          (sht:tbl-put img 'ImageHeight (* hw sc))))
      (sht:tbl-put img 'Rotation (cond ((cdr (assoc 50 ed))) (0.0)))
      (sht:tbl-put img 'Origin (vlax-3d-point (sht:sheet-pt ed lx ly)))
      (vla-put-Layer img *sht:LayFmt*)
      (sht:sign-xd-set en "LOGO" (caddr s) 0 lx ly kw (strcat "I:" path))))
  en)

;; Слой подписей: нет — создать (есть — не трогать: заморозка / выключение — выбор пользователя)
(defun sht:sign-layer ()
  (if (not (tblsearch "LAYER" *sht:LaySign*))
    (entmake (list '(0 . "LAYER") '(100 . "AcDbSymbolTableRecord") '(100 . "AcDbLayerTableRecord")
                   (cons 2 *sht:LaySign*) '(70 . 0) '(62 . 7) '(6 . "Continuous") '(370 . -3)))))

;; Слой заблокирован — разблокировать (возвращает имя, чтобы потом заблокировать обратно)
(defun sht:lay-unlock (name / en ed fl)
  (if (and (setq en (tblobjname "LAYER" name))
           (setq ed (entget en))
           (= 4 (logand 4 (setq fl (cond ((cdr (assoc 70 ed))) (0))))))
    (progn
      (entmod (sht:dxf-set ed 70 (logand fl (~ 4))))
      name)))

(defun sht:lay-lock (name / en ed)
  (if (setq en (tblobjname "LAYER" name))
    (progn
      (setq ed (entget en))
      (entmod (sht:dxf-set ed 70 (logior (cond ((cdr (assoc 70 ed))) (0)) 4))))))

;; Лист для сверки: (ename entget handle слоты)
(defun sht:sign-sheet (en cfg)
  (list en (entget en) (vla-get-Handle (vlax-ename->vla-object en))
        (sht:sign-want (sht:sheet-info en) (sht:attrs en) cfg)))

;; Сверить подписи и логотип со штампами всех листов; force — всё заново.
;; Возвращает (поставлено убрано нет-блоков ошибки) или nil (ошибка — сообщение уже написано).
(defun sht:sign-sync (force / cfg lk r)
  (setq *sht:BoxCache* nil
        *sht:BlkReal*  nil
        *sht:SignMiss* nil
        cfg            (sht:sign-cfg (sht:set-read)))
  (if (sht:sign-on-p cfg) (sht:sign-layer))
  ;; заблокированные слои подписей, листа и текущий (на нём вставка рождается) — на время сверки открыть
  (setq lk (vl-remove nil (mapcar 'sht:lay-unlock (sht:uniq-ci (list *sht:LaySign* *sht:LayFmt* (getvar "CLAYER")))))
        r  (vl-catch-all-apply 'sht:sign-sync0 (list force cfg)))
  (foreach l lk (sht:lay-lock l))
  (if (vl-catch-all-error-p r)
    (progn
      (princ (strcat "\nSHEETS: подписи и логотип не сверены: " (vl-catch-all-error-message r)))
      nil)
    r))

(defun sht:sign-sync0 (force cfg / shs s w keep slot made del errs r)
  (setq made 0
        del  0
        shs  (mapcar '(lambda (en) (sht:sign-sheet en cfg)) (sht:sheets)))
  ;; что есть: на своём месте у своего листа и нужно листу — остаётся (по одному на графу), иначе — удалить
  (foreach o (sht:sign-objs)
    (setq s    (vl-some '(lambda (x) (if (= (caddr x) (nth 2 o)) x)) shs)
          w    (if s (vl-some '(lambda (x) (if (and (= (car x) (nth 1 o)) (= (cadr x) (nth 3 o))
                                                    (= (caddr x) (nth 7 o)))
                                                x))
                              (nth 3 s)))
          slot (if w (list (caddr s) (car w) (cadr w))))
    (if (and (not force) w (not (member slot keep)) (sht:sign-at-p o (cadr s)))
      (setq keep (cons slot keep))
      (if (not (vl-catch-all-error-p (vl-catch-all-apply 'entdel (list (car o)))))
        (setq del (1+ del)))))
  ;; чего нет — поставить
  (foreach s shs
    (foreach w (nth 3 s)
      (if (not (member (list (caddr s) (car w) (cadr w)) keep))
        (progn
          (setq r (vl-catch-all-apply 'sht:sign-put (list s w)))
          (cond
            ((vl-catch-all-error-p r)
             (setq r (strcat (if (= (car w) "LOGO") "Логотип" (strcat "Подпись (строка " (itoa (cadr w)) ")"))
                             " на листе " (sht:sheet-no (car s)) " не поставлен"
                             (if (= (car w) "LOGO") "" "а") ": " (vl-catch-all-error-message r)))
             (if (not (member r errs)) (setq errs (cons r errs))))
            (r (setq made (1+ made))))))))
  (list made del *sht:SignMiss* (reverse errs)))

;; Сообщение: all — и когда ничего не менялось
(defun sht:sign-msg (r all / chg)
  (setq chg (or (> (car r) 0) (> (cadr r) 0)))
  (if (or all chg)
    (princ (strcat "\nПодписи и логотип: "
                   (if chg (strcat "поставлено " (itoa (car r)) ", убрано " (itoa (cadr r))) "всё на местах")
                   ".")))
  (if (and (caddr r) (or all chg))
    (princ (strcat "\n  Нет в чертеже блока: " (sht:join (caddr r) ", ") " - не ставится (SHEET_SIGN).")))
  (foreach e (cadddr r) (princ (strcat "\n  " e))))

;; Автосверка (без «всё заново»), если подписи или логотип заданы. quiet — без сообщения.
(defun sht:sign-auto (quiet / r)
  (if (and (not *sht:SignBusy*) (sht:sign-on-p (sht:sign-cfg (sht:set-read))))
    (progn
      (setq *sht:SignBusy* T
            r              (vl-catch-all-apply 'sht:sign-sync (list nil))
            *sht:SignBusy* nil)
      (cond
        ((vl-catch-all-error-p r)
         (princ (strcat "\nSHEETS: подписи и логотип не сверены: " (vl-catch-all-error-message r)))
         nil)
        (r
         (if (not quiet) (sht:sign-msg r nil))
         r)))))

;; Наблюдать за листами (вставки и фамилии NAME1-6), если подписи или логотип заданы:
;; лист сдвинули, повернули, фамилию поменяли — флаг *sht:SignDirty* (сверка — в конце команды)
(defun sht:sign-watch ( / objs)
  (if *sht:RSign* (vlr-remove *sht:RSign*))
  (setq *sht:RSign* nil)
  (if (sht:sign-on-p (sht:sign-cfg (sht:set-read)))
    (foreach en (sht:sheets)
      (setq objs (cons (vlax-ename->vla-object en) objs))
      (foreach a (sht:att-objs en)
        (if (member (strcase (vla-get-TagString a)) *sht:NameTags*)
          (setq objs (cons a objs))))))
  (if objs
    (setq *sht:RSign* (vlr-object-reactor objs "SHEETS" '((:vlr-modified . sht:r-sign-mod)))))
  (length objs))

(defun sht:r-sign-mod (obj r args)
  (setq *sht:SignDirty* T)
  (princ))

;; --- окно «Подписи и логотип» ---------------------------------------------------
;; Переменные окна (локальные в c:SHEET_SIGN): sht:gnames — (("Иванов" . листов) …), sht:gmap —
;; фамилия -> блок, sht:gblks — блоки для выбора, sht:gfiles — (блок . файл) из файлов DWG (загрузятся
;; после «Расставить»), sht:gsel — выбранная строка, sht:gfit — "1" / "0"; логотип: sht:lkind
;; "N" / "B" / "I", sht:lblk, sht:lpath, sht:lfit.

;; Фамилии на листах форм 3, 4, 5 (графа 11, строки 1-6): (("Иванов" . листов) …), по строкам, затем по листам
(defun sht:sign-names (ens / al i nm res n out)
  (foreach en ens
    (if (sht:sign-rows (caddr (sht:sheet-info en)))
      (setq al (cons (sht:attrs en) al))))
  (setq al (reverse al)
        i  1)
  (repeat 6
    (foreach a al
      (setq nm (sht:trim (cdr (assoc (strcat "NAME" (itoa i)) a))))
      (if (and (/= nm "") (not (member nm res)))
        (setq res (append res (list nm)))))
    (setq i (1+ i)))
  (foreach nm res
    (setq n 0)
    (foreach a al
      (if (vl-some '(lambda (k) (= (sht:trim (cdr (assoc k a))) nm)) *sht:NameTags*)
        (setq n (1+ n))))
    (setq out (append out (list (cons nm n)))))
  out)

;; Блоки чертежа для выбора: без листов SHT_*, анонимных, внешних ссылок и их блоков, «_…»
(defun sht:user-blocks ( / r n fl res)
  (setq r (tblnext "BLOCK" T))
  (while r
    (setq n  (cdr (assoc 2 r))
          fl (cond ((cdr (assoc 70 r))) (0)))
    (if (not (or (wcmatch n "`**,_*,SHT_*,*|*") (/= 0 (logand fl 21))))
      (setq res (cons n res)))
    (setq r (tblnext "BLOCK")))
  (vl-sort res '<))

;; Блок для фамилии: в имени блока есть фамилия (самое длинное слово без точек, без учёта регистра);
;; несколько — с «подп» в имени; нет — ""
(defun sht:sign-guess (nm blks / w hits)
  (setq w "")
  (foreach x (sht:split (sht:trim nm) " ")
    (if (and (not (vl-string-search "." x)) (> (strlen x) (strlen w))) (setq w x)))
  (setq w (sht:lc w))
  (if (> (strlen w) 1)
    (foreach b blks
      (if (vl-string-search w (sht:lc b)) (setq hits (append hits (list b))))))
  (cond ((null hits) "")
        ((vl-some '(lambda (b) (if (vl-string-search "подп" (sht:lc b)) b)) hits))
        (t (car hits))))

;; Номер блока b в списке выбора (0 — «нет»)
(defun sht:pos1 (b lst / i)
  (if (and b (setq i (vl-position b lst))) (1+ i) 0))

(defun sht:sign-line (p / b)
  (setq b (cond ((cdr (assoc (car p) sht:gmap))) ("")))
  (strcat (car p) "\t" (if (= b "") "(без подписи)" b) (if (assoc b sht:gfiles) " (из файла)" "")
          "\t" (itoa (cdr p)) (if (= (cdr p) 1) " лист" " листов")))

(defun sht:sign-info ( / n)
  (setq n 0)
  (foreach p sht:gnames
    (if (/= (cond ((cdr (assoc (car p) sht:gmap))) ("")) "") (setq n (1+ n))))
  (if sht:gnames
    (strcat "Фамилий в штампах: " (itoa (length sht:gnames)) ", с подписью: " (itoa n)
            ". Выберите фамилию в списке, затем блок подписи.")
    "В штампах (графа 11) фамилий нет - впишите их: SHEET_DATA (данные комплекта)."))

;; Заполнить окно по переменным (список, выбор блоков, логотип)
;; s0.14.3: выбранная строка списка фамилий (sht:gsel) или nil — без nth
(defun sht:sign-cur ( / i r)
  (if (not (numberp sht:gsel)) (setq sht:gsel 0))
  (setq i 0)
  (foreach q sht:gnames
    (if (= i sht:gsel) (setq r q))
    (setq i (1+ i)))
  (if (and r (listp r)) r))

(defun sht:sign-fill ( / p)
  (setq *sht:Step* "окно: список фамилий")
  (start_list "sht_GList")
  (foreach q sht:gnames
    (setq *sht:Step* (strcat "окно: строка списка " (vl-prin1-to-string q)))
    (add_list (sht:sign-line q)))
  (end_list)
  (setq *sht:Step* "окно: выбранная фамилия")
  (setq p (sht:sign-cur))
  (setq *sht:Step* "окно: список блоков подписи")
  (sht:set-popup "sht_GBlk" (cons "(без подписи)" sht:gblks)
                 (if p (sht:pos1 (cdr (assoc (car p) sht:gmap)) sht:gblks) 0))
  (setq *sht:Step* "окно: доступность выбора блока")
  (if p (set_tile "sht_GList" (itoa sht:gsel)))
  (mode_tile "sht_GBlk" (if p 0 1))
  (mode_tile "sht_GFile" (if p 0 1))
  (setq *sht:Step* "окно: строка сведений")
  (set_tile "sht_GInfo" (sht:sign-info))
  (setq *sht:Step* "окно: список блоков логотипа")
  (sht:set-popup "sht_LgBlk" (cons "(не выбран)" sht:gblks) (sht:pos1 sht:lblk sht:gblks))
  (setq *sht:Step* "окно: логотип - путь и вид")
  (set_tile "sht_LgPath" sht:lpath)
  (set_tile "sht_LgKind" (cond ((= sht:lkind "B") "sht_LgKindB") ((= sht:lkind "I") "sht_LgKindI") (t "sht_LgKindN")))
  (setq *sht:Step* "окно: доступность полей логотипа")
  (sht:sign-lmodes))

;; Доступность полей логотипа по виду
(defun sht:sign-lmodes ()
  (mode_tile "sht_LgBlk" (if (= sht:lkind "B") 0 1))
  (mode_tile "sht_LgBFile" (if (= sht:lkind "B") 0 1))
  (mode_tile "sht_LgFit" (if (= sht:lkind "B") 0 1))
  (mode_tile "sht_LgPath" (if (= sht:lkind "I") 0 1))
  (mode_tile "sht_LgBrowse" (if (= sht:lkind "I") 0 1)))

(defun sht:sign-init ()
  (sht:sign-fill)
  (setq *sht:Step* "окно: переключатели и примечание")
  (set_tile "sht_GFit" (if (= sht:gfit "0") "sht_GFit0" "sht_GFit1"))
  (set_tile "sht_LgFit" (if (= sht:lfit "0") "sht_LgFit0" "sht_LgFit1"))
  (set_tile "sht_GNote" (strcat "Подписи - слой " *sht:LaySign* " (заморозить - печать без подписей), логотип - слой "
                                *sht:LayFmt* ". Двигаются вместе с листом, меняются с фамилией."))
  (setq *sht:Step* "окно: действия кнопок")
  (action_tile "sht_GList" "(sht:sign-pick $value)")
  (action_tile "sht_GBlk" "(sht:sign-blk $value)")
  (action_tile "sht_GFile" "(sht:sign-file \"G\")")
  (action_tile "sht_GFit" "(setq sht:gfit (if (= $value \"sht_GFit0\") \"0\" \"1\"))")
  (action_tile "sht_LgKind" "(sht:sign-lkind $value)")
  (action_tile "sht_LgBlk" "(sht:sign-lblk $value)")
  (action_tile "sht_LgBFile" "(sht:sign-file \"L\")")
  (action_tile "sht_LgPath" "(setq sht:lpath (sht:trim $value))")
  (action_tile "sht_LgBrowse" "(sht:sign-browse)")
  (action_tile "sht_LgFit" "(setq sht:lfit (if (= $value \"sht_LgFit0\") \"0\" \"1\"))")
  (action_tile "accept" "(sht:sign-ok)"))

(defun sht:sign-pick (v)
  (setq sht:gsel (atoi v))
  (sht:sign-fill))

(defun sht:sign-blk (v / p i)
  (setq i (atoi v))
  (if (setq p (sht:sign-cur))
    (setq sht:gmap (sht:alist-put sht:gmap (car p) (if (> i 0) (nth (1- i) sht:gblks) ""))))
  (sht:sign-fill))

(defun sht:sign-lkind (v)
  (setq sht:lkind (cond ((= v "sht_LgKindB") "B") ((= v "sht_LgKindI") "I") (t "N")))
  (sht:sign-lmodes))

(defun sht:sign-lblk (v / i)
  (setq i       (atoi v)
        sht:lblk (if (> i 0) (nth (1- i) sht:gblks) "")))

;; «Из файла DWG...»: блок загрузится из файла после «Расставить» (имя блока — имя файла);
;; target "G" — подпись выбранной фамилии, "L" — логотип
(defun sht:sign-file (target / f b p)
  (setq sht:lpath (sht:trim (get_tile "sht_LgPath"))
        f         (getfiled "Блок из файла DWG" "" "dwg" 0))
  (if f
    (progn
      (setq b (vl-filename-base f))
      (if (not (member b sht:gblks))
        (setq sht:gblks  (vl-sort (cons b sht:gblks) '<)
              sht:gfiles (cons (cons b f) sht:gfiles)))
      (cond
        ((= target "L") (setq sht:lkind "B" sht:lblk b))
        ((setq p (sht:sign-cur))
         (setq sht:gmap (sht:alist-put sht:gmap (car p) b))))
      (sht:sign-fill))))

;; «...» картинки логотипа
(defun sht:sign-browse ( / f)
  (setq f (getfiled "Логотип - картинка" (sht:trim (get_tile "sht_LgPath")) *sht:ImgExt* 0))
  (if f
    (progn
      (setq sht:lpath f
            sht:lkind "I")
      (sht:sign-fill))))

(defun sht:sign-ok ()
  (setq sht:lpath (sht:trim (get_tile "sht_LgPath")))
  (cond
    ((and (= sht:lkind "B") (= sht:lblk ""))
     (set_tile "error" "Логотип: выберите блок (или «Нет»)."))
    ((and (= sht:lkind "I") (= sht:lpath ""))
     (set_tile "error" "Логотип: укажите файл картинки (или «Нет»)."))
    ((and (= sht:lkind "I") (not (findfile sht:lpath)))
     (set_tile "error" (strcat "Нет файла картинки: " sht:lpath)))
    (t (done_dialog 1))))

(defun sht:sign-dialog ( / dcl_id dclFile ret)
  (setq ret 0)
  (setq *sht:Step* "окно: загрузка DCL")
  (if (sht:dlg-load)
    (if (new_dialog "sht_sign" dcl_id)
      (progn
        (setq *sht:Step* "окно: заполнение"
              *sht:SignErr* (vl-catch-all-apply 'sht:sign-init nil))
        (if (vl-catch-all-error-p *sht:SignErr*)
          (progn                                   ; s0.14.2: окно закрыть, ошибку — в команду
            (setq *sht:SignErr* (vl-catch-all-error-message *sht:SignErr*))
            (vl-catch-all-apply '(lambda () (done_dialog 0)) nil)
            (vl-catch-all-apply '(lambda () (start_dialog)) nil)
            (setq ret -1))
          (progn
            (setq *sht:SignErr* nil
                  *sht:Step*    "окно открыто")
            (setq ret (start_dialog))
            (setq *sht:Step* "окно закрыто"))))
      (princ "\nSHEETS: не удалось открыть окно.")))
  (sht:dlg-cleanup)
  ret)

;; Загрузить описание блока из файла DWG (имя — имя файла): -INSERT имя=файл и отмена на точке вставки
;; (в чертеже ничего не вставляется; не вышло — ActiveX). Блок с таким именем уже есть — взять его.
;; Возвращает имя или nil.
(defun sht:blk-from-file (f / b ce ins)
  (setq b (vl-filename-base f))
  ;; s0.14.3: сначала ActiveX — вставка из файла и сразу удалить (остаётся описание блока)
  (if (not (tblsearch "BLOCK" b))
    (progn
      (setq ins (vl-catch-all-apply 'vla-InsertBlock (list (sht:ms) (vlax-3d-point 0.0 0.0 0.0) f 1.0 1.0 1.0 0.0)))
      (if (not (vl-catch-all-error-p ins))
        (vl-catch-all-apply 'entdel (list (vlax-vla-object->ename ins))))))
  ;; запасной путь — -INSERT имя=файл и отмена на точке вставки
  (if (not (tblsearch "BLOCK" b))
    (progn
      (setq ce (getvar "CMDECHO"))
      (setvar "CMDECHO" 0)
      (command "_.-INSERT" (strcat b "=" f))
      (command)
      (setvar "CMDECHO" ce)))
  (if (tblsearch "BLOCK" b)
    b
    (progn
      (princ (strcat "\nSHEETS: блок из файла не загружен: " f))
      nil)))

;; Настройки окна — в словарь чертежа (если поменялись). Фамилии — только те, что сейчас в штампах
;; (прежние записи убираются: иначе «подписи заданы» оставалось бы и без фамилий на листах).
(defun sht:sign-save ( / sdat new)
  (setq sdat (sht:set-read))
  (foreach p sdat
    (if (not (and (> (strlen (car p)) 6) (= (substr (car p) 1 6) "@SIGN:")))
      (setq new (append new (list p)))))
  (foreach p sht:gnames
    (setq new (sht:alist-put new (strcat "@SIGN:" (car p)) (cond ((cdr (assoc (car p) sht:gmap))) ("")))))
  (setq new (sht:alist-put new "@SIGNFIT" sht:gfit)
        new (sht:alist-put new "@LOGO" (cond ((= sht:lkind "B") (strcat "B:" sht:lblk))
                                             ((= sht:lkind "I") (strcat "I:" sht:lpath))
                                             (t "")))
        new (sht:alist-put new "@LOGOFIT" sht:lfit))
  (if (not (equal new sdat)) (sht:set-write new)))

;; Подписи и логотип: какой блок у какой фамилии, логотип; «Расставить» — на всех листах заново
;; s0.14.1: команда — обёртка: ошибка перехватывается, в строку — шаг (*sht:Step*) и текст ошибки,
;; отметка отмены закрывается. Переменные окна — локальные здесь (окно и sht:sign-cmd видят их).
(defun c:SHEET_SIGN ( / res sht:undo
                        sht:gnames sht:gmap sht:gblks sht:gfiles sht:gsel sht:gfit
                        sht:lkind sht:lblk sht:lpath sht:lfit)
  (setq *sht:Step* "начало"
        res        (vl-catch-all-apply 'sht:sign-cmd nil))
  (if (vl-catch-all-error-p res)
    (progn
      (if sht:undo (vl-catch-all-apply 'vla-EndUndoMark (list (sht:doc))))
      (princ (strcat "\nSHEETS: SHEET_SIGN - сбой на шаге «" (cond (*sht:Step*) ("?")) "»: "
                     (vl-catch-all-error-message res) ". Пришлите эту строку разработчику."))))
  (princ))

(defun sht:sign-cmd ( / doc sdat cfg lg ret r)
  (setq *sht:Step* "подготовка (стиль, слои, блоки листов)")
  (setq doc  (sht:doc)
        sdat (sht:prepare))
  (setq *sht:Step* "двойной щелчок (UNDEFINE EATTEDIT)")
  (sht:dblclick-setup)
  (setq *sht:Step* "настройки подписей из чертежа")
  (setq cfg        (sht:sign-cfg sdat))
  (setq *sht:Step* "фамилии в штампах")
  (setq sht:gnames (sht:sign-names (sht:sheets)))
  (setq *sht:Step* "блоки чертежа")
  (setq sht:gblks  (sht:user-blocks))
  (setq *sht:Step* "разбор настроек")
  (setq sht:gmap   (car cfg)
        sht:gsel   0
        sht:gfit   (cadr cfg)
        sht:lfit   (cadddr cfg)
        lg         (caddr cfg))
  (setq *sht:Step* "угадать блоки подписей")
  ;; фамилия без записи — блок угадать по имени (в окне видно, можно поменять)
  (foreach p sht:gnames
    (if (not (assoc (car p) sht:gmap))
      (setq sht:gmap (sht:alist-put sht:gmap (car p) (sht:sign-guess (car p) sht:gblks)))))
  (cond
    ((= (substr lg 1 2) "B:") (setq sht:lkind "B" sht:lblk (substr lg 3) sht:lpath ""))
    ((= (substr lg 1 2) "I:") (setq sht:lkind "I" sht:lblk "" sht:lpath (substr lg 3)))
    (t (setq sht:lkind "N" sht:lblk "" sht:lpath "")))
  (setq *sht:Step* "окно")
  (setq ret (sht:sign-dialog))
  (if (= ret -1)
    (princ (strcat "\nSHEETS: SHEET_SIGN - сбой на шаге «" (cond (*sht:Step*) ("?")) "»: "
                   (cond (*sht:SignErr*) ("?")) ". Окно закрыто. Пришлите эту строку разработчику.")))
  (if (= ret 1)
    (progn
      (setq *sht:Step* "блоки из файлов")
      (vla-StartUndoMark doc)
      (setq sht:undo T)
      ;; блоки из файлов — только выбранные
      (foreach f sht:gfiles
        (if (or (vl-some '(lambda (p) (= (cdr p) (car f))) sht:gmap)
                (and (= sht:lkind "B") (= sht:lblk (car f))))
          (sht:blk-from-file (cdr f))))
      (setq *sht:Step* "запись настроек")
      (sht:sign-save)
      (setq *sht:Step* "расстановка на листах")
      (setq r (sht:sign-sync T))
      (vla-EndUndoMark doc)
      (setq sht:undo nil)
      (setq *sht:Step* "сообщение")
      (if r (sht:sign-msg r T)))
    (if (/= ret -1) (princ "\nПодписи и логотип: без изменений.")))
  (setq *sht:Step* "наблюдение за листами")
  (sht:watch)
  (setq *sht:Step* "готово")
  (princ))


;;; --------------------------------------------------------------------------
;;;  17. ОКНО ВСЕХ КОМАНД: SHT (s0.8) и АВТОЗАГРУЗКА
;;;  Кнопка закрывает окно кодом (done_dialog), команда запускается после закрытия:
;;;  из открытого окна command и выбор в чертеже нельзя. «Вкл./выкл.» — окно открывается снова.
;;;  Автозагрузка: строка в acaddoc.lsp (грузится при открытии каждого чертежа):
;;;    (if (and (/= (getenv "SHT_AutoLoad") "0") (findfile "SHEETS.lsp")) (load "SHEETS.lsp" ""))
;;;  + папка SHEETS.lsp — в пути поддержки и в доверенных (TRUSTEDPATHS);
;;;  выключение — SHT_AutoLoad = "0" (строка в acaddoc.lsp остаётся, ничего не делает).
;;; --------------------------------------------------------------------------

(setq *sht:AlTag* ";; SHEETS autoload (SHT)")

;; Папка без «\» в конце, для сравнения — строчными
(defun sht:dir-key (d)
  (setq d (sht:trim d))
  (while (and (> (strlen d) 0) (member (substr d (strlen d)) '("\\" "/")))
    (setq d (substr d 1 (1- (strlen d)))))
  (sht:lc (vl-string-translate "/" "\\" d)))

;; Есть ли папка d в списке путей «a;b;c»
(defun sht:path-has (paths d / k)
  (setq k (sht:dir-key d))
  (vl-some '(lambda (x) (= (sht:dir-key x) k)) (sht:split (cond (paths) ("")) ";")))

;; Добавить папку в список путей (если её там нет)
(defun sht:path-add (paths d / s)
  (setq s (sht:trim (cond (paths) (""))))
  (cond
    ((sht:path-has s d) s)
    ((= s "") d)
    ((= (substr s (strlen s)) ";") (strcat s d))
    (t (strcat s ";" d))))

;; Есть ли в файле строка автозагрузки SHEETS
(defun sht:al-has (fn / f s r)
  (if (and fn (findfile fn) (setq f (open fn "r")))
    (progn
      (while (and (not r) (setq s (read-line f)))
        (if (vl-string-search "SHEETS autoload" s) (setq r T)))
      (close f)))
  r)

;; Состояние автозагрузки: (код файл): 0 — не настроена, 1 — выключена, 2 — включена,
;; 3 — включена, но SHEETS.lsp не находится в путях поддержки
(defun sht:al-state ( / fn)
  (setq fn (findfile "acaddoc.lsp"))
  (cond
    ((not (sht:al-has fn)) (list 0 fn))
    ((= (getenv "SHT_AutoLoad") "0") (list 1 fn))
    ((not (findfile "SHEETS.lsp")) (list 3 fn))
    (t (list 2 fn))))

(defun sht:al-text ( / st)
  (setq st (sht:al-state))
  (cond
    ((= (car st) 2) (strcat "Автозагрузка при открытии чертежа: включена (" (cadr st) ")"))
    ((= (car st) 1) "Автозагрузка при открытии чертежа: выключена")
    ((= (car st) 3) "Автозагрузка: включена, но SHEETS.lsp не найден в путях - включите заново")
    (t "Автозагрузка при открытии чертежа: не настроена")))

;; Путь поддержки AutoCAD (Настройка - Файлы): прочитать / записать; nil — не вышло
(defun sht:support-files ( / r)
  (setq r (vl-catch-all-apply 'vla-get-Files (list (vla-get-Preferences (vlax-get-acad-object)))))
  (if (vl-catch-all-error-p r) nil r))

;; Включить автозагрузку. Возвращает T, если всё записано.
(defun sht:autoload-on ( / lsp dir nm files sp r tp fn adir f ok)
  (setq lsp (findfile "SHEETS.lsp"))
  (if (not lsp)
    (setq lsp (getfiled "Где лежит SHEETS.lsp (для автозагрузки)" "" "lsp" 0)))
  (cond
    ((not lsp)
     (princ "\nАвтозагрузка: файл SHEETS.lsp не выбран - ничего не изменено.")
     nil)
    (t
     (setq dir (vl-filename-directory lsp)
           nm  (strcat (vl-filename-base lsp) ".lsp"))
     ;; 1. Папка — в путь поддержки (чтобы (load "SHEETS.lsp") нашёл файл)
     (if (setq files (sht:support-files))
       (progn
         (setq sp (vl-catch-all-apply 'vla-get-SupportPath (list files)))
         (if (and (not (vl-catch-all-error-p sp)) (not (sht:path-has sp dir)))
           (progn
             (setq r (vl-catch-all-apply 'vla-put-SupportPath (list files (sht:path-add sp dir))))
             (if (vl-catch-all-error-p r)
               (princ (strcat "\nАвтозагрузка: папку не удалось добавить в путь поддержки: " dir))
               (princ (strcat "\nПапка добавлена в путь поддержки: " dir)))))))
     ;; 2. Файл acaddoc.lsp: тот, что AutoCAD уже находит, иначе — новый в папке Support пользователя
     (setq fn (findfile "acaddoc.lsp"))
     (if (not fn)
       (progn
         (setq adir (strcat (cond ((getvar "ROAMABLEROOTPREFIX")) ("")) "Support"))
         (if (not (vl-file-directory-p adir)) (setq adir dir))
         (setq fn (strcat (vl-string-right-trim "\\" adir) "\\acaddoc.lsp"))))
     ;; 3. Обе папки — в доверенные (без вопроса «Загрузить файл?» при каждом открытии)
     (setq tp (getvar "TRUSTEDPATHS"))
     (foreach d (list dir (vl-filename-directory fn))
       (setq tp (sht:path-add tp d)))
     (if (/= tp (getvar "TRUSTEDPATHS"))
       (if (vl-catch-all-error-p (vl-catch-all-apply 'setvar (list "TRUSTEDPATHS" tp)))
         (princ "\nАвтозагрузка: доверенные папки (TRUSTEDPATHS) не изменены - AutoCAD может спрашивать «Загрузить?».")))
     ;; 4. Строка автозагрузки (один раз; только латиница — кодировка файла не важна)
     (cond
       ((sht:al-has fn) (setq ok T))
       ((setq f (open fn "a"))
        (write-line "" f)                         ; если последняя строка без перевода строки
        (write-line *sht:AlTag* f)
        (write-line (strcat (chr 40) "if " (chr 40) "and " (chr 40) "/= " (chr 40) "getenv \"SHT_AutoLoad\""
                            (chr 41) " \"0\"" (chr 41) " " (chr 40) "findfile \"" nm "\"" (chr 41) (chr 41)
                            " " (chr 40) "load \"" nm "\" \"\"" (chr 41) (chr 41)) f)
        (close f)
        (setq ok T))
       (t (princ (strcat "\nАвтозагрузка: не удалось записать файл " fn))))
     (if ok
       (progn
         (setenv "SHT_AutoLoad" "1")
         (princ (strcat "\nАвтозагрузка включена: " fn
                        " - SHEETS будет загружаться при открытии каждого чертежа (в этой версии AutoCAD)."))))
     ok)))

(defun sht:autoload-off ()
  (setenv "SHT_AutoLoad" "0")
  (princ "\nАвтозагрузка выключена (строка в acaddoc.lsp осталась и ничего не делает; включить - SHT, «Вкл./выкл.»)."))

(defun sht:autoload-toggle ()
  (if (= (car (sht:al-state)) 2) (sht:autoload-off) (sht:autoload-on)))

;; Сведения о чертеже для окна: (строка1 строка2)
(defun sht:main-info (en / shs nn sdat s1 s2)
  (setq shs  (sht:sheets)
        sdat (sht:set-read)
        nn   0)
  (foreach q shs
    (if (= (sht:trim (cdr (assoc "SHEET" (sht:attrs q)))) "") (setq nn (1+ nn))))
  (setq s1 (strcat "Листов SHEETS: " (itoa (length shs))
                   (if (> nn 0) (strcat " (без номера: " (itoa nn) ")") "")
                   (if en
                     (strcat ". Выбран лист "
                             (if (= (setq s2 (sht:trim (cdr (assoc "SHEET" (sht:attrs en))))) "") "без номера" s2))
                     ""))
        s2 (strcat "Ведомость листов: " (if (sht:kind-tables "LIST") "есть" "нет")
                   ". Ведомость спецификаций: " (if (sht:kind-tables "SPEC") "есть" "нет")
                   ". Ссылочных: " (if (sht:kind-tables "REFS") "есть" "нет")
                   ". Подписи и логотип: " (if (sht:sign-on-p (sht:sign-cfg sdat)) "заданы" "нет") "."))
  (list s1 s2))

(defun sht:main-init (en / inf)
  (setq inf (sht:main-info en))
  (set_tile "sht_MInfo1" (car inf))
  (set_tile "sht_MInfo2" (cadr inf))
  (set_tile "sht_MDblTx" (if (= (getenv "SHT_DblClick") "0")
                           "Двойной щелчок по листу: обычный редактор атрибутов"
                           "Двойной щелчок по листу: окно «Лист»"))
  (set_tile "sht_MAutoTx" (sht:al-text))
  (set_tile "sht_MEdit" (if en "Изменить выбранный лист..." "Изменить лист <"))
  (set_tile "sht_MStamp" (if en "Все поля штампа (выбранный лист)..." "Все поля штампа <"))
  (foreach p '(("sht_MNew" . 2) ("sht_MEdit" . 3) ("sht_MData" . 4) ("sht_MUpd" . 5)
               ("sht_MList" . 6) ("sht_MSpec" . 7) ("sht_MSign" . 8) ("sht_MPlot" . 9)
               ("sht_MDbl" . 10) ("sht_MAuto" . 11) ("sht_MProbe" . 12) ("sht_MRefs" . 13)
               ("sht_MSide" . 14) ("sht_MStamp" . 15) ("sht_MSpds" . 16))
    (action_tile (car p) (strcat (chr 40) "done_dialog " (itoa (cdr p)) (chr 41)))))

(defun sht:main-dialog (en / dcl_id dclFile ret)
  (setq ret 0)
  (if (sht:dlg-load)
    (if (new_dialog "sht_main" dcl_id)
      (progn
        (sht:main-init en)
        (setq ret (start_dialog)))
      (princ "\nSHEETS: не удалось открыть окно.")))
  (sht:dlg-cleanup)
  ret)

;; SHT — окно всех команд SHEETS. Лист, выбранный до команды, — для «Изменить лист».
(defun c:SHT ( / ss en ret again)
  (sht:dblclick-setup)
  (if (and (setq ss (ssget "_I")) (sht:sheet-p (ssname ss 0)))
    (setq en (ssname ss 0)))
  (setq again T)
  (while again
    (setq again nil
          ret   (sht:main-dialog (if (and en (entget en)) en)))
    (cond
      ((= ret 2) (c:SHEET_NEW))
      ((= ret 3)
       (if (and en (entget en))
         (progn
           (sssetfirst nil nil)
           (sht:edit-sheet en)
           (sht:watch))
         (c:SHEET_EDIT)))
      ((= ret 4) (c:SHEET_DATA))
      ((= ret 5) (c:SHEET_UPDATE))
      ((= ret 6) (c:SHEET_LIST))
      ((= ret 7) (c:SHEET_SPEC))
      ((= ret 8) (c:SHEET_SIGN))
      ((= ret 9) (c:SHEET_PLOT))
      ((= ret 10) (c:SHEET_DBLCLICK) (setq again T))
      ((= ret 11) (sht:autoload-toggle) (setq again T))
      ((= ret 12) (c:SHEET_PROBE))
      ((= ret 13) (c:SHEET_REFS))
      ((= ret 14) (c:SHEET_SIDE))
      ((= ret 16) (c:SHEET_FROM_SPDS))
      ((= ret 15)
       (if (and en (entget en))
         (progn
           (sssetfirst nil nil)
           (sht:fw-edit en 'STAMP)
           (sht:watch))
         (c:SHEET_STAMP)))))
  (princ))



;;; --------------------------------------------------------------------------
;;;  18. ПЕРЕВОД ЛИСТОВ СПДС В SHEETS (s0.12): SHEET_FROM_SPDS
;;;  Рамка СПДС (объект SPDSFORMAT) хранит поля парами 301 «имя поля» -> 300 / 40 / 90 / 290 «значение».
;;;  Соответствие полей — по заполненным рамкам Артёма (формы 3, 4, 5, 6, боковой штамп; 2026-10-06).
;;;  Подписи СПДС: строка 1 — нижняя; у SHEETS ROLE1 — верхняя. Изменения: у СПДС и SHEETS 1 — нижняя.
;;;  На месте рамки — лист SHEETS той же формы, формата, ориентации и масштаба (левый нижний угол);
;;;  старая рамка — на выключенный слой *sht:SpdsLay* (решение Артёма); переведённые повторно не берутся.
;;; --------------------------------------------------------------------------

(setq *sht:SpdsLay* "0000_СПДС_старые")

;; Подписи (формы 3, 4 — строки 1-6, форма 5 — 1-5): должность, фамилия, дата
(setq *sht:SpdsSign*
  '(("Add.text5" . "ROLE1") ("Author" . "NAME1") ("Author(date)" . "DATE1")
    ("Add.text6" . "ROLE2") ("Control" . "NAME2") ("Control(date)" . "DATE2")
    ("Add.text" . "ROLE3") ("Add.subject" . "NAME3") ("Add.subject(date)" . "DATE3")
    ("Add.text2" . "ROLE4") ("Add.subject2" . "NAME4") ("Add.subject2(date)" . "DATE4")
    ("Add.text3" . "ROLE5") ("Add.subject3" . "NAME5") ("Add.subject3(date)" . "DATE5")
    ("Add.text4" . "ROLE6") ("Add.subject4" . "NAME6") ("Add.subject4(date)" . "DATE6")))

;; Боковой штамп: «Согласовано» — 4 столбца (должность, фамилия, подпись, дата); подпись (Name 3, 4) — нет
(setq *sht:SpdsSide*
  '(("Original#" . "INV") ("Instead#" . "VZAM")
    ("Role1" . "SOGL1R") ("Name 1" . "SOGL1N") ("Name 5" . "SOGL1D")
    ("Role2" . "SOGL2R") ("Name 2" . "SOGL2N") ("Name 6" . "SOGL2D")))

;; Поля по формам («Лист» формы 4 — раньше «Sheet»: пустое значение не затирает непустое)
(setq *sht:SpdsForm*
  '(("3" ("Designation" . "SHIFR") ("ComplexName" . "OBJECT") ("DrawingName1" . "BUILDING")
         ("Drawing type" . "TITLE") ("Stage" . "STAGE") ("Sheet" . "SHEET") ("Enterprise" . "ORG"))
    ("4" ("Designation" . "OBOZN") ("ComplexName" . "TITLE") ("Drawing type" . "MATER") ("Stage" . "STAGE")
         ("Масса" . "MASS") ("Масштаб" . "SCALE") ("Лист" . "SHEET") ("Sheet" . "SHEET") ("Enterprise" . "ORG"))
    ("5" ("Designation" . "OBOZN") ("DrawingName1" . "TITLE") ("Stage" . "STAGE") ("Sheet" . "SHEET")
         ("Enterprise" . "ORG"))
    ("6" ("Designation" . "SHIFR") ("Sheet" . "SHEET"))))

;; Строки изменений: поле СПДС + номер строки -> C<строка><поле>
(setq *sht:SpdsChg*
  '(("ChangeNr" . "IZM") ("ChangeSector" . "KOL") ("ChangeSheet" . "LST") ("ChangeDoc" . "DOC")
    ("ChangeDate" . "DAT")))

;; Поля СПДС, которые не переносятся и не попадают в отчёт (служебные, подписи, «Листов» — сам)
(setq *sht:SpdsSkip*
  '("Name" "Info" "Scale" "Format" "DimScale" "Autonumerated" "First sheet" "Show zones" "Extended view"
    "Zone" "idTemplate" "Orientation" "Multiplicity" "Std version" "GOST2013.5mm" "Text style"
    "ObliqueByStyle" "XScaleByStyle" "PaperBound" "OriginX" "OriginY" "SheetCount"))

(defun sht:spds-skip-p (k)
  (or (member k *sht:SpdsSkip*)
      (vl-string-search "(sign)" k)
      (= (substr k 1 10) "ChangeSign")
      (= (substr k 1 9) "Sign&date")))

;; Поля рамки: (("имя" . значение) …) в порядке записи
(defun sht:spds-data (ed / key res)
  (foreach g ed
    (cond ((= (car g) 301) (setq key (cdr g)))
          ((and key (member (car g) '(1 40 70 90 290 300)))
           (setq res (cons (cons key (cdr g)) res)
                 key nil))))
  (reverse res))

(defun sht:spds-str (v) (if (= (type v) 'STR) v ""))

;; Форма листа SHEETS по набору полей рамки; без поля «Инв. № подл.» — без бокового штампа ("N")
(defun sht:spds-form (dat / k f)
  (setq k (mapcar 'car dat)
        f (cond ((or (member "Масса" k) (member "Масштаб" k)) "4")
                ((not (member "Author" k)) "6")
                ((or (and (member "ChangeNr3" k) (not (member "ChangeNr1" k)))
                     (and (member "Add.text3" k) (not (member "Add.text4" k))))
                 "5")
                (t "3")))
  (if (member "Original#" k) f (strcat f "N")))

;; Номера строк изменений рамки по возрастанию (у формы 5 СПДС — 3, 4; у формы 6 — 1, 2)
(defun sht:spds-chg-idx (dat / res k s)
  (foreach p dat
    (setq k (car p))
    (foreach c *sht:SpdsChg*
      (if (and (> (strlen k) (strlen (car c)))
               (= (substr k 1 (strlen (car c))) (car c))
               (sht:int-p (setq s (substr k (1+ (strlen (car c))))))
               (not (member (atoi s) res)))
        (setq res (cons (atoi s) res)))))
  (vl-sort res '<))

;; Значения атрибутов листа из полей рамки -> (значения непереносимые-непустые)
(defun sht:spds-vals (dat form / map vals unk tag v i)
  (setq map (append (cdr (assoc (sht:fbase form) *sht:SpdsForm*))
                    (if (/= (sht:fbase form) "6") *sht:SpdsSign*)
                    (if (sht:fside-p form) *sht:SpdsSide*)
                    '(("PageNumber" . "PNUM")))
        i   0)
  (foreach n (sht:spds-chg-idx dat)
    (setq i (1+ i))
    (if (<= i (sht:chg-rows form))
      (foreach c *sht:SpdsChg*
        (setq map (append map (list (cons (strcat (car c) (itoa n)) (strcat "C" (itoa i) (cdr c)))))))))
  (foreach p dat
    (setq v (sht:spds-str (cdr p)))
    (cond
      ((setq tag (cdr (assoc (car p) map)))
       (if (or (/= (sht:trim v) "") (not (assoc tag vals)))
         (setq vals (sht:alist-put vals tag v))))
      ((sht:spds-skip-p (car p)) nil)
      ((/= (sht:trim v) "") (setq unk (append unk (list (cons (car p) v)))))))
  (list vals unk))

;; Формат, ориентация, масштаб и левый нижний угол рамки -> (запись ориентация масштаб точка)
;; или строка — причина, почему рамка не переводится
(defun sht:spds-geom (en ed dat / fmt mult rec ori sc o r mn mx wh lab tol)
  (setq fmt  (sht:spds-str (cdr (assoc "Format" dat)))
        mult (cdr (assoc "Multiplicity" dat))
        sc   (cdr (assoc "Scale" dat))
        ori  (sht:parse-orient (sht:spds-str (cdr (assoc "Orientation" dat)))))
  (if (not (and (numberp mult) (> mult 0))) (setq mult 1))
  (setq mult (fix mult))
  (if (not (and (numberp sc) (> sc 0))) (setq sc (cdr (assoc 48 ed))))
  (if (not (and (numberp sc) (> sc 0))) (setq sc 1.0))
  (setq lab (if (> mult 1) (strcat fmt "x" (itoa mult)) fmt)
        rec (if (/= fmt "") (sht:parse-fmt lab)))
  (cond
    ((not rec) (strcat "формат «" lab "» - нет среди форматов SHEETS"))
    ((not ori) "не распознана ориентация")
    ((and (= ori "L") (sht:portrait-only-p (car rec) (cadr rec)))
     (strcat (sht:fmt-label rec) " горизонтальный в SHEETS не предусмотрен"))
    (t
     (setq wh (mapcar '(lambda (x) (* x sc)) (sht:fmt-wh rec ori))
           o  (vlax-ename->vla-object en)
           r  (vl-catch-all-apply 'vla-GetBoundingBox (list o 'mn 'mx)))
     (if (vl-catch-all-error-p r)
       ;; габарита нет — угол из полей рамки
       (list rec ori sc (list (cond ((cdr (assoc "OriginX" dat))) (0.0))
                              (cond ((cdr (assoc "OriginY" dat))) (0.0)) 0.0))
       (progn
         (setq mn  (vlax-safearray->list mn)
               mx  (vlax-safearray->list mx)
               tol (max 1.0 (* 0.005 (car wh))))
         (if (and (equal (- (car mx) (car mn)) (car wh) tol)
                  (equal (- (cadr mx) (cadr mn)) (cadr wh) tol))
           (list rec ori sc (list (car mn) (cadr mn) 0.0))
           (strcat "размер рамки " (sht:n2s (- (car mx) (car mn))) " x " (sht:n2s (- (cadr mx) (cadr mn)))
                   " не совпадает с форматом " (sht:fmt-label rec) " 1:" (sht:n2s sc) " "
                   (chr 40) (sht:n2s (car wh)) " x " (sht:n2s (cadr wh)) (chr 41)
                   " - рамка повёрнута?")))))))

;; Подпись рамки для отчёта: «рамка 2E8, лист 21»
(defun sht:spds-label (ed dat / s)
  (setq s (sht:trim (sht:spds-str (cdr (assoc "Sheet" dat)))))
  (if (= s "") (setq s (sht:trim (sht:spds-str (cdr (assoc "Лист" dat))))))
  (strcat "рамка " (cond ((cdr (assoc 5 ed))) ("?")) (if (= s "") "" (strcat ", лист " s))))

(defun sht:lay-locked-p (lay / r)
  (and (setq r (tblsearch "LAYER" lay))
       (= 4 (logand 4 (cond ((cdr (assoc 70 r))) (0))))))

;; Слой старых рамок: есть — выключить, нет — создать выключенным
(defun sht:spds-layer ( / en ed)
  (if (setq en (tblobjname "LAYER" *sht:SpdsLay*))
    (progn
      (setq ed (entget en))
      (entmod (sht:dxf-set ed 62 (- (abs (cond ((cdr (assoc 62 ed))) (8)))))))
    (entmake (list '(0 . "LAYER") '(100 . "AcDbSymbolTableRecord") '(100 . "AcDbLayerTableRecord")
                   (cons 2 *sht:SpdsLay*) '(70 . 0) '(62 . -8) '(6 . "Continuous")))))

;; Перевести одну рамку -> (T лист форма непереносимые рамка-на-слое) или (nil причина)
(defun sht:spds-one (en / ed dat form g v base new r)
  (setq ed   (entget en)
        dat  (sht:spds-data ed)
        form (sht:spds-form dat)
        g    (sht:spds-geom en ed dat))
  (cond
    ((= (type g) 'STR) (list nil g))
    ((sht:lay-locked-p (cdr (assoc 8 ed)))
     (list nil (strcat "рамка на заблокированном слое «" (cdr (assoc 8 ed)) "»")))
    (t
     (setq v (sht:spds-vals dat form))
     ;; все поля формы — явно (пустые не получат значений по умолчанию, напр. «Разработал»)
     (foreach at (sht:attr-tab form)
       (if (not (member (car at) '("FORMAT" "ORIENT")))
         (setq base (cons (cons (car at) "") base))))
     (setq new (vl-catch-all-apply 'sht:insert
                 (list (car g) (cadr g) form (cadddr g) (caddr g) (append (car v) base))))
     (if (vl-catch-all-error-p new)
       (list nil (strcat "лист не вставлен: " (vl-catch-all-error-message new)))
       (progn
         (setq r (vl-catch-all-apply 'vla-put-Layer (list (vlax-ename->vla-object en) *sht:SpdsLay*)))
         (list T new form (cadr v) (not (vl-catch-all-error-p r))))))))

(defun sht:spds-form-name (f)
  (strcat "форма " (sht:fbase f) (if (sht:fside-p f) "" " без бокового штампа")))

;; Повторяющиеся номера листов (в своей группе нумерации) -> ("лист 21 - 2 раза" …)
(defun sht:spds-dups (ens / gl seen res n)
  (setq gl (sht:gnums ens))
  (foreach p gl
    (if (not (member p seen))
      (progn
        (setq seen (cons p seen)
              n    0)
        (foreach q gl (if (and (= (car q) (car p)) (= (strcase (cdr q)) (strcase (cdr p)))) (setq n (1+ n))))
        (if (> n 1)
          (setq res (append res (list (strcat (if (= (car p) "M") "" (strcat (substr (car p) 3) ", "))
                                              "лист " (cdr p) " - " (itoa n) " раза"))))))))
  res)

(defun sht:spds-cut (s) (if (> (strlen s) 40) (strcat (substr s 1 37) "...") s))

;; SHEET_FROM_SPDS — листы СПДС -> листы SHEETS
(defun c:SHEET_FROM_SPDS ( / doc sdat ens0 kw ss i en ed frames npaper nlay ok bad unk cnt r p s
                             lr sr dups diff nolay)
  (setq doc  (sht:doc)
        sdat (sht:prepare)
        ens0 (sht:sheets))
  (sht:dblclick-setup)
  (initget "Все Указать")
  (setq kw (getkword "\nПеревести рамки СПДС в листы SHEETS [Все/Указать] <Все>: "))
  (setq ss (if (= kw "Указать")
             (progn (princ "\nВыберите рамки СПДС: ") (ssget '((0 . "SPDSFORMAT"))))
             (ssget "_X" '((0 . "SPDSFORMAT"))))
        npaper 0
        nlay   0)
  (if ss
    (progn
      (setq i 0)
      (while (< i (sslength ss))
        (setq en (ssname ss i)
              ed (entget en)
              i  (1+ i))
        (cond ((/= (strcase (cond ((cdr (assoc 410 ed))) ("Model"))) "MODEL") (setq npaper (1+ npaper)))
              ((= (strcase (cdr (assoc 8 ed))) (strcase *sht:SpdsLay*)) (setq nlay (1+ nlay)))
              (t (setq frames (cons en frames)))))))
  (setq frames (reverse frames))
  (cond
    ((null frames)
     (princ (strcat "\nРамок СПДС для перевода нет"
                    (if (> nlay 0) (strcat " (переведённые раньше - на слое «" *sht:SpdsLay* "»: " (itoa nlay) ")") "")
                    (if (> npaper 0) (strcat "; в листах (не в модели): " (itoa npaper)) "")
                    ".")))
    (t
     (vla-StartUndoMark doc)
     (sht:spds-layer)
     (foreach en frames
       (setq ed (entget en)
             s  (sht:spds-label ed (sht:spds-data ed))
             r  (sht:spds-one en))
       (if (car r)
         (progn
           (setq ok (append ok (list (cadr r))))
           (if (setq p (assoc (caddr r) cnt))
             (setq cnt (subst (cons (car p) (1+ (cdr p))) p cnt))
             (setq cnt (append cnt (list (cons (caddr r) 1)))))
           (if (cadddr r) (setq unk (append unk (list (cons s (cadddr r))))))
           (if (not (nth 4 r)) (setq nolay (append nolay (list s)))))
         (setq bad (append bad (list (strcat s ": " (cadr r)))))))
     (if ok
       (progn
         (setq r    (sht:common-now (mapcar 'sht:attrs (sht:sheets)) sdat)
               diff (cadr r))
         ;; листов SHEETS до перевода не было — данные комплекта берутся с переведённых листов
         (if (null ens0)
           (progn
             (foreach q (car r) (setq sdat (sht:alist-put sdat (car q) (cdr q))))
             (sht:set-write sdat)))
         (sht:stage-layer (cdr (assoc "STAGE" (car r))))
         (setq sr (sht:sign-auto T)
               lr (sht:list-auto T))))
     (vla-EndUndoMark doc)
     ;; отчёт
     (princ (strcat "\nПереведено рамок СПДС: " (itoa (length ok))
                    (if cnt
                      (strcat " " (chr 40)
                              (apply 'strcat (mapcar '(lambda (q) (strcat (sht:spds-form-name (car q)) " - "
                                                                          (itoa (cdr q)) "; ")) cnt))
                              (chr 41))
                      "")
                    "."))
     (if ok
       (princ (strcat "\nСтарые рамки - на выключенном слое «" *sht:SpdsLay* "» (включить слой - чтобы сверить).")))
     (foreach q nolay
       (princ (strcat "\n! " q ": рамку не удалось перенести на слой - уберите её вручную.")))
     (if bad
       (progn
         (princ (strcat "\nНе переведено: " (itoa (length bad))))
         (foreach q bad (princ (strcat "\n  - " q)))))
     (if (> nlay 0)
       (princ (strcat "\nПереведённые раньше (слой «" *sht:SpdsLay* "») не тронуты: " (itoa nlay) ".")))
     (if (> npaper 0)
       (princ (strcat "\nРамки в листах (не в модели) не переводятся: " (itoa npaper) ".")))
     (if unk
       (progn
         (princ "\nНе перенесены непустые поля СПДС (в SHEETS для них нет графы):")
         (foreach q unk
           (princ (strcat "\n  - " (car q) ": "
                          (apply 'strcat (mapcar '(lambda (x) (strcat (car x) " = «" (sht:spds-cut (cdr x)) "»; "))
                                                 (cdr q))))))))
     (if (setq dups (sht:spds-dups (sht:sheets)))
       (progn
         (princ "\nПовторяются номера листов (исправить - в окне листа):")
         (foreach q dups (princ (strcat "\n  - " q)))))
     (if (and ok diff)
       (princ (strcat "\nНа листах разные: " (sht:diff-str diff)
                      " - выровнять: SHT -> «Данные комплекта...».")))
     (if lr (sht:list-msg lr nil))
     (if sr (sht:sign-msg sr nil))
     (if (or bad unk dups nolay) (textscr))))
  (sht:watch)
  (princ))



;; Загрузка: прежние реакторы снять, поставить заново. s0.14: в командную строку при загрузке ничего не
;; отправляется (на старте AutoCAD из пакета .bundle SendCommand вешал AutoCAD; в separate namespace строка
;; не видит функций sht:). EATTEDIT отключается в начале команд SHEETS и в SHEET_DBLEDIT (sht:dblclick-setup).
(vl-catch-all-apply 'sht:react-remove nil)
(vl-catch-all-apply 'sht:dbl-restore nil)
(setq *sht:DblOn* nil *sht:DblEn* nil *sht:DblDone* nil *sht:ApplyQ* nil *sht:ListBusy* nil *sht:SignBusy* nil
      *sht:GridErr* nil)
(vl-catch-all-apply 'sht:react-ensure nil)

(princ (strcat "\nSHEETS " *sht:Version* " загружен. Все команды - в окне: SHT "
               "(прежние SHEET_NEW, SHEET_EDIT, SHEET_PLOT ... тоже работают)."))
(princ)
